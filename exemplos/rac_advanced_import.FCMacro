# Gerado por revit-free (rvttool macro) — importador .rvt -> FreeCAD
# Executar dentro do FreeCAD: Macro > Macros... > selecionar este arquivo > Executar
import FreeCAD as App
import Part
doc = App.newDocument("RevitImport")

grp = doc.addObject("App::DocumentObjectGroup", "NIVEL_+0.000")
grp.Label = "NIVEL_+0.000 (linhas de localizacao)"
comp = []
comp.append(Part.LineSegment(App.Vector(-0.203000, -0.000000, 0.000000), App.Vector(53.873202, -0.000000, 0.000000)))
comp.append(Part.LineSegment(App.Vector(53.873202, -0.000000, 0.000000), App.Vector(53.873202, 37.312199, 0.000000)))
comp.append(Part.LineSegment(App.Vector(53.873202, 37.312199, 0.000000), App.Vector(42.596001, 37.312199, 0.000000)))
comp.append(Part.LineSegment(App.Vector(42.596001, 37.312199, 0.000000), App.Vector(42.596001, 17.347801, 0.000000)))
comp.append(Part.LineSegment(App.Vector(42.596001, 17.347801, 0.000000), App.Vector(22.694701, 17.347801, 0.000000)))
comp.append(Part.LineSegment(App.Vector(22.694701, 17.347801, 0.000000), App.Vector(22.694701, 24.212390, 0.000000)))
comp.append(Part.LineSegment(App.Vector(22.694701, 24.212390, 0.000000), App.Vector(16.294300, 24.212390, 0.000000)))
comp.append(Part.LineSegment(App.Vector(16.294300, 24.212390, 0.000000), App.Vector(16.294300, 17.347801, 0.000000)))
comp.append(Part.LineSegment(App.Vector(16.294300, 17.347801, 0.000000), App.Vector(11.048800, 17.347801, 0.000000)))
comp.append(Part.LineSegment(App.Vector(11.048800, 17.347801, 0.000000), App.Vector(11.048800, 66.472878, 0.000000)))
comp.append(Part.LineSegment(App.Vector(11.048800, 66.472878, 0.000000), App.Vector(-0.203000, 66.472878, 0.000000)))
comp.append(Part.LineSegment(App.Vector(-0.203000, 66.472878, 0.000000), App.Vector(-0.203000, -0.000000, 0.000000)))
comp.append(Part.LineSegment(App.Vector(0.000000, 0.000000, 0.000000), App.Vector(66.066878, 0.000000, 0.000000)))
comp.append(Part.LineSegment(App.Vector(66.066878, 0.000000, 0.000000), App.Vector(66.066878, 10.845800, 0.000000)))
comp.append(Part.LineSegment(App.Vector(66.066878, 10.845800, 0.000000), App.Vector(16.941801, 10.845800, 0.000000)))
comp.append(Part.LineSegment(App.Vector(16.941801, 10.845800, 0.000000), App.Vector(16.941801, 42.799001, 0.000000)))
comp.append(Part.LineSegment(App.Vector(16.941801, 42.799001, 0.000000), App.Vector(36.906199, 42.799001, 0.000000)))
comp.append(Part.LineSegment(App.Vector(36.906199, 42.799001, 0.000000), App.Vector(36.906199, 53.670202, 0.000000)))
comp.append(Part.LineSegment(App.Vector(36.906199, 53.670202, 0.000000), App.Vector(0.000000, 53.670202, 0.000000)))
comp.append(Part.LineSegment(App.Vector(0.000000, 53.670202, 0.000000), App.Vector(0.000000, 0.000000, 0.000000)))
comp.append(Part.LineSegment(App.Vector(-11.645901, 0.000000, 0.000000), App.Vector(-5.651500, 0.000000, 0.000000)))
comp.append(Part.LineSegment(App.Vector(-5.651500, 0.000000, 0.000000), App.Vector(-5.651500, 6.864589, 0.000000)))
comp.append(Part.LineSegment(App.Vector(-5.651500, 6.864589, 0.000000), App.Vector(-11.645901, 6.864589, 0.000000)))
comp.append(Part.LineSegment(App.Vector(-11.645901, 6.864589, 0.000000), App.Vector(-11.645901, 0.000000, 0.000000)))
comp.append(Part.LineSegment(App.Vector(0.000000, 0.000000, 0.000000), App.Vector(53.670202, 0.000000, 0.000000)))
comp.append(Part.LineSegment(App.Vector(53.670202, 0.000000, 0.000000), App.Vector(53.670202, 36.906199, 0.000000)))
comp.append(Part.LineSegment(App.Vector(53.670202, 36.906199, 0.000000), App.Vector(42.799001, 36.906199, 0.000000)))
comp.append(Part.LineSegment(App.Vector(42.799001, 36.906199, 0.000000), App.Vector(42.799001, 16.941801, 0.000000)))
comp.append(Part.LineSegment(App.Vector(42.799001, 16.941801, 0.000000), App.Vector(22.379201, 16.941801, 0.000000)))
comp.append(Part.LineSegment(App.Vector(22.379201, 16.941801, 0.000000), App.Vector(22.379201, 17.544900, 0.000000)))
comp.append(Part.LineSegment(App.Vector(22.379201, 17.544900, 0.000000), App.Vector(21.767800, 17.544900, 0.000000)))
comp.append(Part.LineSegment(App.Vector(17.411700, 17.544900, 0.000000), App.Vector(16.609800, 17.544900, 0.000000)))
comp.append(Part.LineSegment(App.Vector(16.609800, 17.544900, 0.000000), App.Vector(16.609800, 16.941801, 0.000000)))
comp.append(Part.LineSegment(App.Vector(16.609800, 16.941801, 0.000000), App.Vector(10.845800, 16.941801, 0.000000)))
comp.append(Part.LineSegment(App.Vector(10.845800, 16.941801, 0.000000), App.Vector(10.845800, 66.066878, 0.000000)))
comp.append(Part.LineSegment(App.Vector(10.845800, 66.066878, 0.000000), App.Vector(0.000000, 66.066878, 0.000000)))
comp.append(Part.LineSegment(App.Vector(0.000000, 66.066878, 0.000000), App.Vector(0.000000, 0.000000, 0.000000)))
comp.append(Part.LineSegment(App.Vector(53.670202, 0.000000, 0.000000), App.Vector(53.670202, 34.266199, 0.000000)))
comp.append(Part.LineSegment(App.Vector(53.670202, 36.906199, 0.000000), App.Vector(48.880202, 36.906199, 0.000000)))
comp.append(Part.LineSegment(App.Vector(10.845800, 66.066878, 0.000000), App.Vector(4.790000, 66.066878, 0.000000)))
comp.append(Part.LineSegment(App.Vector(0.000000, 66.066878, 0.000000), App.Vector(0.000000, 10.951500, 0.000000)))
comp.append(Part.LineSegment(App.Vector(0.000000, 66.066878, 0.000000), App.Vector(0.000000, 63.426878, 0.000000)))
comp.append(Part.LineSegment(App.Vector(42.799001, 16.941801, 0.000000), App.Vector(10.845800, 16.941801, 0.000000)))
comp.append(Part.LineSegment(App.Vector(-16.112852, 0.000000, 0.000000), App.Vector(0.000000, 0.000000, 0.000000)))
comp.append(Part.LineSegment(App.Vector(0.000000, 0.000000, 0.000000), App.Vector(0.000000, 0.303000, 0.000000)))
comp.append(Part.LineSegment(App.Vector(0.000000, 0.303000, 0.000000), App.Vector(-16.112852, 0.303000, 0.000000)))
comp.append(Part.LineSegment(App.Vector(-16.112852, 0.303000, 0.000000), App.Vector(-16.112852, 0.000000, 0.000000)))
comp.append(Part.LineSegment(App.Vector(0.000000, -0.000000, 0.000000), App.Vector(31.854201, -0.000000, 0.000000)))
comp.append(Part.LineSegment(App.Vector(31.854201, 0.000000, 0.000000), App.Vector(31.854201, 8.828599, 0.000000)))
comp.append(Part.LineSegment(App.Vector(31.854201, 8.828599, 0.000000), App.Vector(26.301700, 8.828599, 0.000000)))
comp.append(Part.LineSegment(App.Vector(26.301700, 8.828599, 0.000000), App.Vector(26.301700, 1.964010, 0.000000)))
comp.append(Part.LineSegment(App.Vector(26.301700, 1.964010, 0.000000), App.Vector(20.208300, 1.964010, 0.000000)))
comp.append(Part.LineSegment(App.Vector(20.208300, 1.964010, 0.000000), App.Vector(20.208300, 8.828599, 0.000000)))
comp.append(Part.LineSegment(App.Vector(20.208300, 8.828599, 0.000000), App.Vector(0.000000, 8.828599, 0.000000)))
comp.append(Part.LineSegment(App.Vector(0.000000, 8.828599, 0.000000), App.Vector(0.000000, -0.000000, 0.000000)))
comp.append(Part.LineSegment(App.Vector(0.000000, 0.165139, 0.000000), App.Vector(0.050000, 0.165139, 0.000000)))
comp.append(Part.LineSegment(App.Vector(0.050000, 0.165139, 0.000000), App.Vector(0.050000, 0.015139, 0.000000)))
comp.append(Part.LineSegment(App.Vector(0.050000, 0.015139, 0.000000), App.Vector(0.000000, 0.015139, 0.000000)))
comp.append(Part.LineSegment(App.Vector(0.000000, 0.015139, 0.000000), App.Vector(0.000000, 0.165139, 0.000000)))
comp.append(Part.LineSegment(App.Vector(-0.025000, 0.154057, 0.000000), App.Vector(0.025000, 0.154057, 0.000000)))
comp.append(Part.LineSegment(App.Vector(0.025000, 0.154057, 0.000000), App.Vector(0.025000, 0.004057, 0.000000)))
comp.append(Part.LineSegment(App.Vector(0.025000, 0.004057, 0.000000), App.Vector(-0.025000, 0.004057, 0.000000)))
comp.append(Part.LineSegment(App.Vector(-0.025000, 0.004057, 0.000000), App.Vector(-0.025000, 0.154057, 0.000000)))
comp.append(Part.LineSegment(App.Vector(0.025000, 0.000000, 0.000000), App.Vector(0.980600, 0.000000, 0.000000)))
comp.append(Part.LineSegment(App.Vector(0.980600, 0.000000, 0.000000), App.Vector(0.980600, 2.325000, 0.000000)))
comp.append(Part.LineSegment(App.Vector(0.980600, 2.325000, 0.000000), App.Vector(0.025000, 2.325000, 0.000000)))
comp.append(Part.LineSegment(App.Vector(0.025000, 2.325000, 0.000000), App.Vector(0.025000, 0.000000, 0.000000)))
comp.append(Part.LineSegment(App.Vector(0.075000, 0.017705, 0.000000), App.Vector(-0.075000, 0.017705, 0.000000)))
comp.append(Part.LineSegment(App.Vector(-0.075000, 0.017705, 0.000000), App.Vector(-0.075000, 0.242705, 0.000000)))
comp.append(Part.LineSegment(App.Vector(-0.075000, 0.242705, 0.000000), App.Vector(0.150000, 0.242705, 0.000000)))
comp.append(Part.LineSegment(App.Vector(0.150000, 0.242705, 0.000000), App.Vector(0.150000, 0.092705, 0.000000)))
comp.append(Part.LineSegment(App.Vector(0.150000, 0.092705, 0.000000), App.Vector(0.075000, 0.092705, 0.000000)))
comp.append(Part.LineSegment(App.Vector(0.075000, 0.092705, 0.000000), App.Vector(0.075000, 0.017705, 0.000000)))
comp.append(Part.LineSegment(App.Vector(-3.097200, 0.000000, 0.000000), App.Vector(0.000000, 0.000000, 0.000000)))
comp.append(Part.LineSegment(App.Vector(-0.000000, -0.000000, 0.000000), App.Vector(-1.548600, 1.603229, 0.000000)))
comp.append(Part.LineSegment(App.Vector(-1.548600, 1.603229, 0.000000), App.Vector(-3.097200, -0.000000, 0.000000)))
comp.append(Part.LineSegment(App.Vector(-1.560000, 0.000000, 0.000000), App.Vector(0.000000, 0.000000, 0.000000)))
comp.append(Part.LineSegment(App.Vector(0.000000, 0.000000, 0.000000), App.Vector(0.000000, 1.603229, 0.000000)))
comp.append(Part.LineSegment(App.Vector(0.000000, 1.603229, 0.000000), App.Vector(-0.011400, 1.603229, 0.000000)))
comp.append(Part.LineSegment(App.Vector(-0.011400, 1.603229, 0.000000), App.Vector(-1.560000, 0.000000, 0.000000)))
comp.append(Part.LineSegment(App.Vector(-1.548600, 1.603229, 0.000000), App.Vector(-1.560000, 1.603229, 0.000000)))
comp.append(Part.LineSegment(App.Vector(-1.560000, 1.603229, 0.000000), App.Vector(-1.560000, 0.000000, 0.000000)))
comp.append(Part.LineSegment(App.Vector(-1.560901, 0.000000, 0.000000), App.Vector(0.000000, 0.000000, 0.000000)))
comp.append(Part.LineSegment(App.Vector(0.000000, 1.603229, 0.000000), App.Vector(-0.012301, 1.603229, 0.000000)))
comp.append(Part.LineSegment(App.Vector(-0.012301, 1.603229, 0.000000), App.Vector(-1.560901, 0.000000, 0.000000)))
comp.append(Part.LineSegment(App.Vector(-1.270225, 0.000000, 0.000000), App.Vector(0.000000, 0.000000, 0.000000)))
comp.append(Part.LineSegment(App.Vector(0.000000, 1.603229, 0.000000), App.Vector(-1.270225, 1.603229, 0.000000)))
comp.append(Part.LineSegment(App.Vector(-1.270225, 1.603229, 0.000000), App.Vector(-1.270225, 0.000000, 0.000000)))
comp.append(Part.LineSegment(App.Vector(-1.548600, 1.603229, 0.000000), App.Vector(-1.560901, 1.603229, 0.000000)))
comp.append(Part.LineSegment(App.Vector(-1.560901, 1.603229, 0.000000), App.Vector(-1.560901, 0.000000, 0.000000)))
comp.append(Part.LineSegment(App.Vector(-0.015000, 0.036213, 0.000000), App.Vector(0.015000, 0.036213, 0.000000)))
comp.append(Part.LineSegment(App.Vector(0.015000, 0.036213, 0.000000), App.Vector(0.015000, 0.006213, 0.000000)))
comp.append(Part.LineSegment(App.Vector(0.015000, 0.006213, 0.000000), App.Vector(-0.015000, 0.006213, 0.000000)))
comp.append(Part.LineSegment(App.Vector(-0.015000, 0.006213, 0.000000), App.Vector(-0.015000, 0.036213, 0.000000)))
comp.append(Part.LineSegment(App.Vector(0.000000, 0.048541, 0.000000), App.Vector(0.030000, 0.048541, 0.000000)))
comp.append(Part.LineSegment(App.Vector(0.030000, 0.048541, 0.000000), App.Vector(0.030000, 0.018541, 0.000000)))
comp.append(Part.LineSegment(App.Vector(0.030000, 0.018541, 0.000000), App.Vector(0.000000, 0.018541, 0.000000)))
comp.append(Part.LineSegment(App.Vector(0.000000, 0.018541, 0.000000), App.Vector(0.000000, 0.048541, 0.000000)))
comp.append(Part.LineSegment(App.Vector(-8.280750, -0.000000, 0.000000), App.Vector(-0.069250, -0.000000, 0.000000)))
comp.append(Part.LineSegment(App.Vector(-0.069250, -0.000000, 0.000000), App.Vector(-0.069250, 5.930750, 0.000000)))
comp.append(Part.LineSegment(App.Vector(-0.069250, 5.930750, 0.000000), App.Vector(-8.280750, 5.930750, 0.000000)))
comp.append(Part.LineSegment(App.Vector(-8.280750, 5.930750, 0.000000), App.Vector(-8.280750, -0.000000, 0.000000)))
comp.append(Part.LineSegment(App.Vector(-0.069250, -0.000000, 0.000000), App.Vector(-0.069250, 3.861500, 0.000000)))
comp.append(Part.LineSegment(App.Vector(-0.069250, 3.861500, 0.000000), App.Vector(-8.280750, 3.861500, 0.000000)))
comp.append(Part.LineSegment(App.Vector(-8.280750, 3.861500, 0.000000), App.Vector(-8.280750, -0.000000, 0.000000)))
comp.append(Part.LineSegment(App.Vector(-7.780750, 0.000000, 0.000000), App.Vector(0.000000, 0.000000, 0.000000)))
comp.append(Part.LineSegment(App.Vector(0.000000, 0.000000, 0.000000), App.Vector(7.691650, -0.000000, 0.000000)))
comp.append(Part.LineSegment(App.Vector(7.691650, -0.000000, 0.000000), App.Vector(7.691650, 8.211500, 0.000000)))
comp.append(Part.LineSegment(App.Vector(7.691650, 8.211500, 0.000000), App.Vector(-7.780750, 8.211500, 0.000000)))
comp.append(Part.LineSegment(App.Vector(-7.780750, 8.211500, 0.000000), App.Vector(-7.780750, 0.000000, 0.000000)))
comp.append(Part.LineSegment(App.Vector(-8.211500, 0.000000, 0.000000), App.Vector(-6.035000, 0.000000, 0.000000)))
comp.append(Part.LineSegment(App.Vector(-6.035000, 0.000000, 0.000000), App.Vector(-6.035000, 3.251801, 0.000000)))
comp.append(Part.LineSegment(App.Vector(-6.035000, 3.251801, 0.000000), App.Vector(-8.211500, 3.251801, 0.000000)))
comp.append(Part.LineSegment(App.Vector(-8.211500, 3.251801, 0.000000), App.Vector(-8.211500, 0.000000, 0.000000)))
comp.append(Part.LineSegment(App.Vector(5.471549, 0.000000, 0.000000), App.Vector(8.723350, 0.000000, 0.000000)))
comp.append(Part.LineSegment(App.Vector(8.723350, 0.000000, 0.000000), App.Vector(8.723350, 5.796500, 0.000000)))
comp.append(Part.LineSegment(App.Vector(8.723350, 5.796500, 0.000000), App.Vector(5.471549, 5.796500, 0.000000)))
comp.append(Part.LineSegment(App.Vector(5.471549, 5.796500, 0.000000), App.Vector(5.471549, 0.000000, 0.000000)))
comp.append(Part.LineSegment(App.Vector(-5.865750, -0.000000, 0.000000), App.Vector(-0.069250, -0.000000, 0.000000)))
comp.append(Part.LineSegment(App.Vector(-0.069250, -0.000000, 0.000000), App.Vector(-0.069250, 2.361500, 0.000000)))
comp.append(Part.LineSegment(App.Vector(-0.069250, 2.361500, 0.000000), App.Vector(-5.865750, 2.361500, 0.000000)))
comp.append(Part.LineSegment(App.Vector(-5.865750, 2.361500, 0.000000), App.Vector(-5.865750, -0.000000, 0.000000)))
comp.append(Part.LineSegment(App.Vector(0.069250, 0.000000, 0.000000), App.Vector(2.333049, 0.000000, 0.000000)))
comp.append(Part.LineSegment(App.Vector(2.333049, 0.000000, 0.000000), App.Vector(2.333049, 5.796500, 0.000000)))
comp.append(Part.LineSegment(App.Vector(2.333049, 5.796500, 0.000000), App.Vector(0.069250, 5.796500, 0.000000)))
comp.append(Part.LineSegment(App.Vector(0.069250, 5.796500, 0.000000), App.Vector(0.069250, 0.000000, 0.000000)))
comp.append(Part.LineSegment(App.Vector(-0.069250, -0.000000, 0.000000), App.Vector(-0.069250, 10.930750, 0.000000)))
comp.append(Part.LineSegment(App.Vector(-0.069250, 10.930750, 0.000000), App.Vector(-8.280750, 10.930750, 0.000000)))
comp.append(Part.LineSegment(App.Vector(-8.280750, 10.930750, 0.000000), App.Vector(-8.280750, -0.000000, 0.000000)))
comp.append(Part.LineSegment(App.Vector(11.138500, 0.000000, 0.000000), App.Vector(17.000000, 0.000000, 0.000000)))
comp.append(Part.LineSegment(App.Vector(17.000000, 0.000000, 0.000000), App.Vector(17.000000, 8.211500, 0.000000)))
comp.append(Part.LineSegment(App.Vector(17.000000, 8.211500, 0.000000), App.Vector(11.138500, 8.211500, 0.000000)))
comp.append(Part.LineSegment(App.Vector(11.138500, 8.211500, 0.000000), App.Vector(11.138500, 0.000000, 0.000000)))
comp.append(Part.LineSegment(App.Vector(-8.211500, 0.000000, 0.000000), App.Vector(0.000000, 0.000000, 0.000000)))
comp.append(Part.LineSegment(App.Vector(0.000000, 0.000000, 0.000000), App.Vector(-0.000000, 11.861500, 0.000000)))
comp.append(Part.LineSegment(App.Vector(-0.000000, 11.861500, 0.000000), App.Vector(-8.211500, 11.861500, 0.000000)))
comp.append(Part.LineSegment(App.Vector(-8.211500, 11.861500, 0.000000), App.Vector(-8.211500, 0.000000, 0.000000)))
comp.append(Part.LineSegment(App.Vector(29.138500, 0.000000, 0.000000), App.Vector(35.000000, 0.000000, 0.000000)))
comp.append(Part.LineSegment(App.Vector(35.000000, 0.000000, 0.000000), App.Vector(35.000000, 8.211500, 0.000000)))
comp.append(Part.LineSegment(App.Vector(35.000000, 8.211500, 0.000000), App.Vector(29.138500, 8.211500, 0.000000)))
comp.append(Part.LineSegment(App.Vector(29.138500, 8.211500, 0.000000), App.Vector(29.138500, 0.000000, 0.000000)))
comp.append(Part.LineSegment(App.Vector(35.138500, 0.000000, 0.000000), App.Vector(40.882778, 0.000000, 0.000000)))
comp.append(Part.LineSegment(App.Vector(40.882778, 0.000000, 0.000000), App.Vector(40.882778, 8.211500, 0.000000)))
comp.append(Part.LineSegment(App.Vector(40.882778, 8.211500, 0.000000), App.Vector(35.138500, 8.211500, 0.000000)))
comp.append(Part.LineSegment(App.Vector(35.138500, 8.211500, 0.000000), App.Vector(35.138500, 0.000000, 0.000000)))
comp.append(Part.LineSegment(App.Vector(-2.283750, -0.000000, 0.000000), App.Vector(-0.069250, -0.000000, 0.000000)))
comp.append(Part.LineSegment(App.Vector(-0.069250, -0.000000, 0.000000), App.Vector(-0.069250, 2.517799, 0.000000)))
comp.append(Part.LineSegment(App.Vector(-0.069250, 2.517799, 0.000000), App.Vector(-2.283750, 2.517799, 0.000000)))
comp.append(Part.LineSegment(App.Vector(-2.283750, 2.517799, 0.000000), App.Vector(-2.283750, -0.000000, 0.000000)))
comp.append(Part.LineSegment(App.Vector(2.769250, -0.000000, 0.000000), App.Vector(7.156299, -0.000000, 0.000000)))
comp.append(Part.LineSegment(App.Vector(7.156299, -0.000000, 0.000000), App.Vector(7.156299, 5.811500, 0.000000)))
comp.append(Part.LineSegment(App.Vector(7.156299, 5.811500, 0.000000), App.Vector(2.769250, 5.811500, 0.000000)))
comp.append(Part.LineSegment(App.Vector(2.769250, 5.811500, 0.000000), App.Vector(2.769250, -0.000000, 0.000000)))
comp.append(Part.LineSegment(App.Vector(0.069250, 0.000000, 0.000000), App.Vector(2.630750, 0.000000, 0.000000)))
comp.append(Part.LineSegment(App.Vector(2.630750, 0.000000, 0.000000), App.Vector(2.630750, 5.811500, 0.000000)))
comp.append(Part.LineSegment(App.Vector(2.630750, 5.811500, 0.000000), App.Vector(0.069250, 5.811500, 0.000000)))
comp.append(Part.LineSegment(App.Vector(0.069250, 5.811500, 0.000000), App.Vector(0.069250, 0.000000, 0.000000)))
comp.append(Part.LineSegment(App.Vector(-5.130750, -0.000000, 0.000000), App.Vector(-0.069250, -0.000000, 0.000000)))
comp.append(Part.LineSegment(App.Vector(-0.069250, -0.000000, 0.000000), App.Vector(-0.069250, 8.011500, 0.000000)))
comp.append(Part.LineSegment(App.Vector(-0.069250, 8.011500, 0.000000), App.Vector(-5.130750, 8.011500, 0.000000)))
comp.append(Part.LineSegment(App.Vector(-5.130750, 8.011500, 0.000000), App.Vector(-5.130750, -0.000000, 0.000000)))
comp.append(Part.LineSegment(App.Vector(3.737349, 0.000000, 0.000000), App.Vector(7.198849, 0.000000, 0.000000)))
comp.append(Part.LineSegment(App.Vector(7.198849, 0.000000, 0.000000), App.Vector(7.198849, 3.561500, 0.000000)))
comp.append(Part.LineSegment(App.Vector(7.198849, 3.561500, 0.000000), App.Vector(3.737349, 3.561500, 0.000000)))
comp.append(Part.LineSegment(App.Vector(3.737349, 3.561500, 0.000000), App.Vector(3.737349, 0.000000, 0.000000)))
comp.append(Part.LineSegment(App.Vector(-7.198849, -0.000000, 0.000000), App.Vector(-3.837349, -0.000000, 0.000000)))
comp.append(Part.LineSegment(App.Vector(-3.837349, -0.000000, 0.000000), App.Vector(-3.837349, 2.111500, 0.000000)))
comp.append(Part.LineSegment(App.Vector(-3.837349, 2.111500, 0.000000), App.Vector(-7.198849, 2.111500, 0.000000)))
comp.append(Part.LineSegment(App.Vector(-7.198849, 2.111500, 0.000000), App.Vector(-7.198849, -0.000000, 0.000000)))
comp.append(Part.LineSegment(App.Vector(0.069250, 0.000000, 0.000000), App.Vector(3.298849, 0.000000, 0.000000)))
comp.append(Part.LineSegment(App.Vector(3.298849, 0.000000, 0.000000), App.Vector(3.298849, 2.111500, 0.000000)))
comp.append(Part.LineSegment(App.Vector(3.298849, 2.111500, 0.000000), App.Vector(0.069250, 2.111500, 0.000000)))
comp.append(Part.LineSegment(App.Vector(0.069250, 2.111500, 0.000000), App.Vector(0.069250, 0.000000, 0.000000)))
comp.append(Part.LineSegment(App.Vector(0.100000, 0.000000, 0.000000), App.Vector(8.280750, 0.000000, 0.000000)))
comp.append(Part.LineSegment(App.Vector(8.280750, 0.000000, 0.000000), App.Vector(8.280750, 4.665502, 0.000000)))
comp.append(Part.LineSegment(App.Vector(8.280750, 4.665502, 0.000000), App.Vector(11.672551, 4.665502, 0.000000)))
comp.append(Part.LineSegment(App.Vector(11.672551, 4.665502, 0.000000), App.Vector(11.672551, 10.565502, 0.000000)))
comp.append(Part.LineSegment(App.Vector(11.672551, 10.565502, 0.000000), App.Vector(11.811051, 10.565502, 0.000000)))
comp.append(Part.LineSegment(App.Vector(11.811051, 10.565502, 0.000000), App.Vector(11.811051, 4.734752, 0.000000)))
comp.append(Part.LineSegment(App.Vector(11.811051, 4.734752, 0.000000), App.Vector(14.472551, 4.734752, 0.000000)))
comp.append(Part.LineSegment(App.Vector(14.472551, 4.734752, 0.000000), App.Vector(14.472551, 9.184752, 0.000000)))
comp.append(Part.LineSegment(App.Vector(14.472551, 9.184752, 0.000000), App.Vector(18.140650, 9.184752, 0.000000)))
comp.append(Part.LineSegment(App.Vector(18.140650, 9.184752, 0.000000), App.Vector(18.140650, 12.746252, 0.000000)))
comp.append(Part.LineSegment(App.Vector(18.140650, 12.746252, 0.000000), App.Vector(16.444900, 12.746252, 0.000000)))
comp.append(Part.LineSegment(App.Vector(16.444900, 12.746252, 0.000000), App.Vector(16.444900, 12.846252, 0.000000)))
comp.append(Part.LineSegment(App.Vector(16.444900, 12.846252, 0.000000), App.Vector(-0.000000, 12.846252, 0.000000)))
comp.append(Part.LineSegment(App.Vector(-0.000000, 12.846252, 0.000000), App.Vector(-0.000000, 4.734752, 0.000000)))
comp.append(Part.LineSegment(App.Vector(-0.000000, 4.734752, 0.000000), App.Vector(0.100000, 4.734752, 0.000000)))
comp.append(Part.LineSegment(App.Vector(0.100000, 4.734752, 0.000000), App.Vector(0.100000, 0.000000, 0.000000)))
comp.append(Part.LineSegment(App.Vector(0.000000, 0.000000, 0.000000), App.Vector(0.138500, 0.000000, 0.000000)))
comp.append(Part.LineSegment(App.Vector(0.138500, 0.000000, 0.000000), App.Vector(0.138500, -5.600000, 0.000000)))
comp.append(Part.LineSegment(App.Vector(0.138500, -5.600000, 0.000000), App.Vector(3.800000, -5.600000, 0.000000)))
comp.append(Part.LineSegment(App.Vector(3.800000, -5.600000, 0.000000), App.Vector(3.800000, 2.511500, 0.000000)))
comp.append(Part.LineSegment(App.Vector(3.800000, 2.511500, 0.000000), App.Vector(-3.105301, 2.511500, 0.000000)))
comp.append(Part.LineSegment(App.Vector(-3.105301, 2.511500, 0.000000), App.Vector(-3.105301, -5.600000, 0.000000)))
comp.append(Part.LineSegment(App.Vector(-3.105301, -5.600000, 0.000000), App.Vector(-0.000000, -5.600000, 0.000000)))
comp.append(Part.LineSegment(App.Vector(-0.000000, -5.600000, 0.000000), App.Vector(0.000000, 0.000000, 0.000000)))
comp.append(Part.LineSegment(App.Vector(-12.174551, 0.000000, 0.000000), App.Vector(-7.113051, 0.000000, 0.000000)))
comp.append(Part.LineSegment(App.Vector(-7.113051, -0.000000, 0.000000), App.Vector(-7.113051, 8.111500, 0.000000)))
comp.append(Part.LineSegment(App.Vector(-7.113051, 8.111500, 0.000000), App.Vector(-12.174551, 8.111500, 0.000000)))
comp.append(Part.LineSegment(App.Vector(-12.174551, 8.111500, 0.000000), App.Vector(-12.174551, 0.000000, 0.000000)))
comp.append(Part.LineSegment(App.Vector(0.000000, 0.000000, 0.000000), App.Vector(8.211500, 0.000000, 0.000000)))
comp.append(Part.LineSegment(App.Vector(8.211500, 0.000000, 0.000000), App.Vector(8.211500, 13.930750, 0.000000)))
comp.append(Part.LineSegment(App.Vector(8.211500, 13.930750, 0.000000), App.Vector(2.711500, 13.930750, 0.000000)))
comp.append(Part.LineSegment(App.Vector(2.711500, 13.930750, 0.000000), App.Vector(2.711500, 17.030750, 0.000000)))
comp.append(Part.LineSegment(App.Vector(2.711500, 17.030750, 0.000000), App.Vector(0.100000, 17.030750, 0.000000)))
comp.append(Part.LineSegment(App.Vector(0.100000, 17.030750, 0.000000), App.Vector(0.100000, 14.000000, 0.000000)))
comp.append(Part.LineSegment(App.Vector(0.100000, 14.000000, 0.000000), App.Vector(-0.000000, 14.000000, 0.000000)))
comp.append(Part.LineSegment(App.Vector(-0.000000, 14.000000, 0.000000), App.Vector(0.000000, 0.000000, 0.000000)))
comp.append(Part.LineSegment(App.Vector(-8.225900, 0.000000, 0.000000), App.Vector(0.000000, 0.000000, 0.000000)))
comp.append(Part.LineSegment(App.Vector(0.000000, 0.000000, 0.000000), App.Vector(3.246500, -0.000000, 0.000000)))
comp.append(Part.LineSegment(App.Vector(3.246500, -0.000000, 0.000000), App.Vector(3.246500, 8.211500, 0.000000)))
comp.append(Part.LineSegment(App.Vector(3.246500, 8.211500, 0.000000), App.Vector(-8.225900, 8.211500, 0.000000)))
comp.append(Part.LineSegment(App.Vector(-8.225900, 8.211500, 0.000000), App.Vector(-8.225900, 0.000000, 0.000000)))
comp.append(Part.LineSegment(App.Vector(-0.069250, -0.000000, 0.000000), App.Vector(-0.069250, 8.930750, 0.000000)))
comp.append(Part.LineSegment(App.Vector(-0.069250, 8.930750, 0.000000), App.Vector(-8.280750, 8.930750, 0.000000)))
comp.append(Part.LineSegment(App.Vector(-8.280750, 8.930750, 0.000000), App.Vector(-8.280750, -0.000000, 0.000000)))
comp.append(Part.LineSegment(App.Vector(-0.069250, -0.000000, 0.000000), App.Vector(-0.069250, 5.861500, 0.000000)))
comp.append(Part.LineSegment(App.Vector(-0.069250, 5.861500, 0.000000), App.Vector(-8.280750, 5.861500, 0.000000)))
comp.append(Part.LineSegment(App.Vector(-8.280750, 5.861500, 0.000000), App.Vector(-8.280750, -0.000000, 0.000000)))
comp.append(Part.LineSegment(App.Vector(-40.882778, 0.000000, 0.000000), App.Vector(-37.138500, 0.000000, 0.000000)))
comp.append(Part.LineSegment(App.Vector(-37.138500, 0.000000, 0.000000), App.Vector(-37.138500, 8.211500, 0.000000)))
comp.append(Part.LineSegment(App.Vector(-37.138500, 8.211500, 0.000000), App.Vector(-40.882778, 8.211500, 0.000000)))
comp.append(Part.LineSegment(App.Vector(-40.882778, 8.211500, 0.000000), App.Vector(-40.882778, 0.000000, 0.000000)))
comp.append(Part.LineSegment(App.Vector(-8.387049, 0.000000, 0.000000), App.Vector(-3.325549, 0.000000, 0.000000)))
comp.append(Part.LineSegment(App.Vector(-3.325549, 0.000000, 0.000000), App.Vector(-3.325549, 2.353000, 0.000000)))
comp.append(Part.LineSegment(App.Vector(-3.325549, 2.353000, 0.000000), App.Vector(-0.100000, 2.353000, 0.000000)))
comp.append(Part.LineSegment(App.Vector(-0.100000, 2.353000, 0.000000), App.Vector(-0.100000, 8.164500, 0.000000)))
comp.append(Part.LineSegment(App.Vector(-0.100000, 8.164500, 0.000000), App.Vector(-8.387049, 8.164500, 0.000000)))
comp.append(Part.LineSegment(App.Vector(-8.387049, 8.164500, 0.000000), App.Vector(-8.387049, 0.000000, 0.000000)))
comp.append(Part.LineSegment(App.Vector(-14.687049, 0.000000, 0.000000), App.Vector(-8.525549, 0.000000, 0.000000)))
comp.append(Part.LineSegment(App.Vector(-8.525549, 0.000000, 0.000000), App.Vector(-8.525549, 8.164500, 0.000000)))
comp.append(Part.LineSegment(App.Vector(-8.525549, 8.164500, 0.000000), App.Vector(-14.687049, 8.164500, 0.000000)))
comp.append(Part.LineSegment(App.Vector(-14.687049, 8.164500, 0.000000), App.Vector(-14.687049, 0.000000, 0.000000)))
comp.append(Part.LineSegment(App.Vector(0.000000, 0.000000, 0.000000), App.Vector(8.264500, 0.000000, 0.000000)))
comp.append(Part.LineSegment(App.Vector(8.264500, 0.000000, 0.000000), App.Vector(8.264500, 5.258401, 0.000000)))
comp.append(Part.LineSegment(App.Vector(8.264500, 5.258401, 0.000000), App.Vector(5.911500, 5.258401, 0.000000)))
comp.append(Part.LineSegment(App.Vector(5.911500, 5.258401, 0.000000), App.Vector(5.911500, 7.926500, 0.000000)))
comp.append(Part.LineSegment(App.Vector(5.911500, 7.926500, 0.000000), App.Vector(0.100000, 7.926500, 0.000000)))
comp.append(Part.LineSegment(App.Vector(0.100000, 7.926500, 0.000000), App.Vector(0.100000, 4.930750, 0.000000)))
comp.append(Part.LineSegment(App.Vector(0.100000, 4.930750, 0.000000), App.Vector(-0.000000, 4.930750, 0.000000)))
comp.append(Part.LineSegment(App.Vector(-0.000000, 4.930750, 0.000000), App.Vector(0.000000, 0.000000, 0.000000)))
comp.append(Part.LineSegment(App.Vector(-8.180750, -0.000000, 0.000000), App.Vector(-0.069250, -0.000000, 0.000000)))
comp.append(Part.LineSegment(App.Vector(-0.069250, -0.000000, 0.000000), App.Vector(-0.069250, 4.694252, 0.000000)))
comp.append(Part.LineSegment(App.Vector(-0.069250, 4.694252, 0.000000), App.Vector(3.094900, 4.694252, 0.000000)))
comp.append(Part.LineSegment(App.Vector(3.094900, 4.694252, 0.000000), App.Vector(3.094900, 12.958752, 0.000000)))
comp.append(Part.LineSegment(App.Vector(3.094900, 12.958752, 0.000000), App.Vector(-8.280750, 12.958752, 0.000000)))
comp.append(Part.LineSegment(App.Vector(-8.280750, 12.958752, 0.000000), App.Vector(-8.280750, 4.847252, 0.000000)))
comp.append(Part.LineSegment(App.Vector(-8.280750, 4.847252, 0.000000), App.Vector(-8.180750, 4.847252, 0.000000)))
comp.append(Part.LineSegment(App.Vector(-8.180750, 4.847252, 0.000000), App.Vector(-8.180750, -0.000000, 0.000000)))
comp.append(Part.LineSegment(App.Vector(-0.069250, -0.000000, 0.000000), App.Vector(-0.069250, 6.492801, 0.000000)))
comp.append(Part.LineSegment(App.Vector(-0.069250, 6.492801, 0.000000), App.Vector(-8.180750, 6.492801, 0.000000)))
comp.append(Part.LineSegment(App.Vector(-8.180750, 6.492801, 0.000000), App.Vector(-8.180750, -0.000000, 0.000000)))
comp.append(Part.LineSegment(App.Vector(-0.069250, -0.000000, 0.000000), App.Vector(-0.069250, 5.461500, 0.000000)))
comp.append(Part.LineSegment(App.Vector(-0.069250, 5.461500, 0.000000), App.Vector(-8.180750, 5.461500, 0.000000)))
comp.append(Part.LineSegment(App.Vector(-8.180750, 5.461500, 0.000000), App.Vector(-8.180750, 0.000000, 0.000000)))
comp.append(Part.LineSegment(App.Vector(-0.069250, -0.000000, 0.000000), App.Vector(-0.069250, 9.861500, 0.000000)))
comp.append(Part.LineSegment(App.Vector(-0.069250, 9.861500, 0.000000), App.Vector(-8.280750, 9.861500, 0.000000)))
comp.append(Part.LineSegment(App.Vector(-8.280750, 9.861500, 0.000000), App.Vector(-8.280750, -0.000000, 0.000000)))
comp.append(Part.LineSegment(App.Vector(-7.015100, 0.000000, 0.000000), App.Vector(0.000000, 0.000000, 0.000000)))
comp.append(Part.LineSegment(App.Vector(0.000000, 0.000000, 0.000000), App.Vector(2.457300, -0.000000, 0.000000)))
comp.append(Part.LineSegment(App.Vector(2.457300, -0.000000, 0.000000), App.Vector(2.457300, 8.211500, 0.000000)))
comp.append(Part.LineSegment(App.Vector(2.457300, 8.211500, 0.000000), App.Vector(-7.015100, 8.211500, 0.000000)))
comp.append(Part.LineSegment(App.Vector(-7.015100, 8.211500, 0.000000), App.Vector(-7.015100, -0.000000, 0.000000)))
comp.append(Part.LineSegment(App.Vector(-0.069250, -0.000000, 0.000000), App.Vector(-0.069250, 7.861500, 0.000000)))
comp.append(Part.LineSegment(App.Vector(-0.069250, 7.861500, 0.000000), App.Vector(-8.280750, 7.861500, 0.000000)))
comp.append(Part.LineSegment(App.Vector(-8.280750, 7.861500, 0.000000), App.Vector(-8.280750, -0.000000, 0.000000)))
comp.append(Part.LineSegment(App.Vector(-40.882778, 0.000000, 0.000000), App.Vector(-31.138500, 0.000000, 0.000000)))
comp.append(Part.LineSegment(App.Vector(-31.138500, 0.000000, 0.000000), App.Vector(-31.138500, 8.211500, 0.000000)))
comp.append(Part.LineSegment(App.Vector(-31.138500, 8.211500, 0.000000), App.Vector(-40.882778, 8.211500, 0.000000)))
comp.append(Part.LineSegment(App.Vector(-0.000000, -0.000000, 0.000000), App.Vector(2.569250, 0.000000, 0.000000)))
comp.append(Part.LineSegment(App.Vector(2.569250, 0.000000, 0.000000), App.Vector(2.569250, 15.961352, 0.000000)))
comp.append(Part.LineSegment(App.Vector(2.569250, 15.961352, 0.000000), App.Vector(-0.000000, 15.961352, 0.000000)))
comp.append(Part.LineSegment(App.Vector(-0.000000, 15.961352, 0.000000), App.Vector(-0.000000, -0.000000, 0.000000)))
comp.append(Part.LineSegment(App.Vector(0.000000, 0.000000, 0.000000), App.Vector(0.049500, 0.000000, 0.000000)))
comp.append(Part.LineSegment(App.Vector(0.049500, 0.000000, 0.000000), App.Vector(0.049500, -5.539000, 0.000000)))
comp.append(Part.LineSegment(App.Vector(0.049500, -5.539000, 0.000000), App.Vector(0.846401, -5.539000, 0.000000)))
comp.append(Part.LineSegment(App.Vector(0.846401, -5.539000, 0.000000), App.Vector(0.846401, -5.764000, 0.000000)))
comp.append(Part.LineSegment(App.Vector(0.846401, -5.764000, 0.000000), App.Vector(0.049500, -5.764000, 0.000000)))
comp.append(Part.LineSegment(App.Vector(0.049500, -5.764000, 0.000000), App.Vector(0.049500, -11.533401, 0.000000)))
comp.append(Part.LineSegment(App.Vector(0.049500, -11.533401, 0.000000), App.Vector(0.846401, -11.533401, 0.000000)))
comp.append(Part.LineSegment(App.Vector(0.846401, -11.533401, 0.000000), App.Vector(0.846401, -11.758401, 0.000000)))
comp.append(Part.LineSegment(App.Vector(0.846401, -11.758401, 0.000000), App.Vector(0.049500, -11.758401, 0.000000)))
comp.append(Part.LineSegment(App.Vector(0.049500, -11.758401, 0.000000), App.Vector(0.049500, -22.133401, 0.000000)))
comp.append(Part.LineSegment(App.Vector(0.049500, -22.133401, 0.000000), App.Vector(0.846401, -22.133401, 0.000000)))
comp.append(Part.LineSegment(App.Vector(0.846401, -22.133401, 0.000000), App.Vector(0.846401, -22.358401, 0.000000)))
comp.append(Part.LineSegment(App.Vector(0.846401, -22.358401, 0.000000), App.Vector(0.049500, -22.358401, 0.000000)))
comp.append(Part.LineSegment(App.Vector(0.049500, -22.358401, 0.000000), App.Vector(0.049500, -29.896401, 0.000000)))
comp.append(Part.LineSegment(App.Vector(0.049500, -29.896401, 0.000000), App.Vector(0.846401, -29.896401, 0.000000)))
comp.append(Part.LineSegment(App.Vector(0.846401, -29.896401, 0.000000), App.Vector(0.846401, -30.121401, 0.000000)))
comp.append(Part.LineSegment(App.Vector(0.846401, -30.121401, 0.000000), App.Vector(0.049500, -30.121401, 0.000000)))
comp.append(Part.LineSegment(App.Vector(0.049500, -30.121401, 0.000000), App.Vector(0.049500, -31.953201, 0.000000)))
comp.append(Part.LineSegment(App.Vector(0.049500, -31.953201, 0.000000), App.Vector(-0.000000, -31.953201, 0.000000)))
comp.append(Part.LineSegment(App.Vector(-0.000000, -31.953201, 0.000000), App.Vector(-0.000000, -34.590652, 0.000000)))
comp.append(Part.LineSegment(App.Vector(-0.000000, -34.590652, 0.000000), App.Vector(8.672051, -34.590652, 0.000000)))
comp.append(Part.LineSegment(App.Vector(8.672051, -34.590652, 0.000000), App.Vector(8.672051, -34.515652, 0.000000)))
comp.append(Part.LineSegment(App.Vector(8.672051, -34.515652, 0.000000), App.Vector(8.810551, -34.515652, 0.000000)))
comp.append(Part.LineSegment(App.Vector(8.810551, -34.515652, 0.000000), App.Vector(8.810551, -18.402800, 0.000000)))
comp.append(Part.LineSegment(App.Vector(8.810551, -18.402800, 0.000000), App.Vector(8.741301, -18.402800, 0.000000)))
comp.append(Part.LineSegment(App.Vector(8.741301, -18.402800, 0.000000), App.Vector(8.741301, -16.595850, 0.000000)))
comp.append(Part.LineSegment(App.Vector(8.741301, -16.595850, 0.000000), App.Vector(9.622372, -16.595850, 0.000000)))
comp.append(Part.LineSegment(App.Vector(9.622372, -16.595850, 0.000000), App.Vector(9.622372, -14.734350, 0.000000)))
comp.append(Part.LineSegment(App.Vector(9.622372, -14.734350, 0.000000), App.Vector(8.741301, -14.734350, 0.000000)))
comp.append(Part.LineSegment(App.Vector(8.741301, -14.734350, 0.000000), App.Vector(8.741301, -8.595850, 0.000000)))
comp.append(Part.LineSegment(App.Vector(8.741301, -8.595850, 0.000000), App.Vector(8.741301, -4.595850, 0.000000)))
comp.append(Part.LineSegment(App.Vector(8.741301, -4.595850, 0.000000), App.Vector(8.741301, 2.595800, 0.000000)))
comp.append(Part.LineSegment(App.Vector(8.741301, 2.595800, 0.000000), App.Vector(8.679801, 2.595800, 0.000000)))
comp.append(Part.LineSegment(App.Vector(8.679801, 2.595800, 0.000000), App.Vector(8.679801, 3.580050, 0.000000)))
comp.append(Part.LineSegment(App.Vector(8.679801, 3.580050, 0.000000), App.Vector(6.039801, 3.580050, 0.000000)))
comp.append(Part.LineSegment(App.Vector(6.039801, 3.580050, 0.000000), App.Vector(6.039801, 2.595800, 0.000000)))
comp.append(Part.LineSegment(App.Vector(6.039801, 2.595800, 0.000000), App.Vector(3.439801, 2.595800, 0.000000)))
comp.append(Part.LineSegment(App.Vector(3.439801, 2.595800, 0.000000), App.Vector(0.000000, 2.595800, 0.000000)))
comp.append(Part.LineSegment(App.Vector(0.000000, 2.595800, 0.000000), App.Vector(0.000000, 0.000000, 0.000000)))
comp.append(Part.LineSegment(App.Vector(0.000000, 0.000000, 0.000000), App.Vector(8.105750, 0.000000, 0.000000)))
comp.append(Part.LineSegment(App.Vector(8.105750, 0.000000, 0.000000), App.Vector(8.105750, 5.711500, 0.000000)))
comp.append(Part.LineSegment(App.Vector(8.105750, 5.711500, 0.000000), App.Vector(8.105750, 8.280750, 0.000000)))
comp.append(Part.LineSegment(App.Vector(8.105750, 8.280750, 0.000000), App.Vector(8.105750, 8.419250, 0.000000)))
comp.append(Part.LineSegment(App.Vector(8.105750, 8.419250, 0.000000), App.Vector(8.333750, 8.419250, 0.000000)))
comp.append(Part.LineSegment(App.Vector(8.333750, 8.419250, 0.000000), App.Vector(8.333750, 17.091301, 0.000000)))
comp.append(Part.LineSegment(App.Vector(8.333750, 17.091301, 0.000000), App.Vector(8.333750, 17.950650, 0.000000)))
comp.append(Part.LineSegment(App.Vector(8.333750, 17.950650, 0.000000), App.Vector(5.980750, 17.950650, 0.000000)))
comp.append(Part.LineSegment(App.Vector(5.980750, 17.950650, 0.000000), App.Vector(0.100000, 17.950650, 0.000000)))
comp.append(Part.LineSegment(App.Vector(0.100000, 17.950650, 0.000000), App.Vector(0.100000, 16.444900, 0.000000)))
comp.append(Part.LineSegment(App.Vector(0.100000, 16.444900, 0.000000), App.Vector(0.000000, 16.444900, 0.000000)))
comp.append(Part.LineSegment(App.Vector(0.000000, 16.444900, 0.000000), App.Vector(0.000000, 0.000000, 0.000000)))
comp.append(Part.LineSegment(App.Vector(0.069250, 0.000000, 0.000000), App.Vector(3.211500, -0.000000, 0.000000)))
comp.append(Part.LineSegment(App.Vector(3.211500, -0.000000, 0.000000), App.Vector(3.211500, 3.087049, 0.000000)))
comp.append(Part.LineSegment(App.Vector(3.211500, 3.087049, 0.000000), App.Vector(0.069250, 3.087049, 0.000000)))
comp.append(Part.LineSegment(App.Vector(0.069250, 3.087049, 0.000000), App.Vector(0.069250, 0.500000, 0.000000)))
comp.append(Part.LineSegment(App.Vector(0.069250, 0.500000, 0.000000), App.Vector(0.069250, 0.000000, 0.000000)))
comp.append(Part.LineSegment(App.Vector(0.069250, 0.000000, 0.000000), App.Vector(2.587049, -0.000000, 0.000000)))
comp.append(Part.LineSegment(App.Vector(2.587049, -0.000000, 0.000000), App.Vector(2.587049, 2.214500, 0.000000)))
comp.append(Part.LineSegment(App.Vector(2.587049, 2.214500, 0.000000), App.Vector(0.069250, 2.214500, 0.000000)))
comp.append(Part.LineSegment(App.Vector(0.069250, 2.214500, 0.000000), App.Vector(0.069250, 0.000000, 0.000000)))
comp.append(Part.LineSegment(App.Vector(0.151500, 0.000000, 0.000000), App.Vector(2.791500, 0.000000, 0.000000)))
comp.append(Part.LineSegment(App.Vector(2.791500, 0.000000, 0.000000), App.Vector(2.791500, 2.600000, 0.000000)))
comp.append(Part.LineSegment(App.Vector(2.791500, 2.600000, 0.000000), App.Vector(2.791500, 5.880750, 0.000000)))
comp.append(Part.LineSegment(App.Vector(2.791500, 5.880750, 0.000000), App.Vector(2.791500, 7.165750, 0.000000)))
comp.append(Part.LineSegment(App.Vector(2.791500, 7.165750, 0.000000), App.Vector(0.151500, 7.165750, 0.000000)))
comp.append(Part.LineSegment(App.Vector(0.151500, 7.165750, 0.000000), App.Vector(0.151500, 0.000000, 0.000000)))
comp.append(Part.LineSegment(App.Vector(0.000000, 0.000000, 0.000000), App.Vector(2.721202, 0.000000, 0.000000)))
comp.append(Part.LineSegment(App.Vector(2.721202, 0.000000, 0.000000), App.Vector(2.721202, 0.151500, 0.000000)))
comp.append(Part.LineSegment(App.Vector(2.721202, 0.151500, 0.000000), App.Vector(3.705452, 0.151500, 0.000000)))
comp.append(Part.LineSegment(App.Vector(3.705452, 0.151500, 0.000000), App.Vector(3.705452, 2.791500, 0.000000)))
comp.append(Part.LineSegment(App.Vector(3.705452, 2.791500, 0.000000), App.Vector(2.568202, 2.791500, 0.000000)))
comp.append(Part.LineSegment(App.Vector(2.568202, 2.791500, 0.000000), App.Vector(2.568202, 3.491500, 0.000000)))
comp.append(Part.LineSegment(App.Vector(2.568202, 3.491500, 0.000000), App.Vector(2.568202, 6.147799, 0.000000)))
comp.append(Part.LineSegment(App.Vector(2.568202, 6.147799, 0.000000), App.Vector(2.568202, 9.157799, 0.000000)))
comp.append(Part.LineSegment(App.Vector(2.568202, 9.157799, 0.000000), App.Vector(2.568202, 12.437799, 0.000000)))
comp.append(Part.LineSegment(App.Vector(2.568202, 12.437799, 0.000000), App.Vector(2.568202, 15.177799, 0.000000)))
comp.append(Part.LineSegment(App.Vector(2.568202, 15.177799, 0.000000), App.Vector(2.568202, 19.137799, 0.000000)))
comp.append(Part.LineSegment(App.Vector(2.568202, 19.137799, 0.000000), App.Vector(2.637452, 19.137799, 0.000000)))
comp.append(Part.LineSegment(App.Vector(2.637452, 19.137799, 0.000000), App.Vector(2.637452, 20.066399, 0.000000)))
comp.append(Part.LineSegment(App.Vector(2.637452, 20.066399, 0.000000), App.Vector(0.000000, 20.066399, 0.000000)))
comp.append(Part.LineSegment(App.Vector(0.000000, 20.066399, 0.000000), App.Vector(0.000000, 0.000000, 0.000000)))
comp.append(Part.LineSegment(App.Vector(0.069250, 0.000000, 0.000000), App.Vector(2.600000, -0.000000, 0.000000)))
comp.append(Part.LineSegment(App.Vector(2.600000, -0.000000, 0.000000), App.Vector(2.600000, 3.516950, 0.000000)))
comp.append(Part.LineSegment(App.Vector(2.600000, 3.516950, 0.000000), App.Vector(0.069250, 3.516950, 0.000000)))
comp.append(Part.LineSegment(App.Vector(0.069250, 3.516950, 0.000000), App.Vector(0.069250, 0.000000, 0.000000)))
comp.append(Part.LineSegment(App.Vector(0.069250, 0.000000, 0.000000), App.Vector(2.569250, 0.000000, 0.000000)))
comp.append(Part.LineSegment(App.Vector(2.569250, 0.000000, 0.000000), App.Vector(5.511500, 0.000000, 0.000000)))
comp.append(Part.LineSegment(App.Vector(5.511500, 0.000000, 0.000000), App.Vector(5.511500, 3.516950, 0.000000)))
comp.append(Part.LineSegment(App.Vector(5.511500, 3.516950, 0.000000), App.Vector(0.950321, 3.516950, 0.000000)))
comp.append(Part.LineSegment(App.Vector(0.950321, 3.516950, 0.000000), App.Vector(0.950321, 1.516950, 0.000000)))
comp.append(Part.LineSegment(App.Vector(0.950321, 1.516950, 0.000000), App.Vector(0.069250, 1.516950, 0.000000)))
comp.append(Part.LineSegment(App.Vector(0.069250, 1.516950, 0.000000), App.Vector(0.069250, 0.000000, 0.000000)))
comp.append(Part.LineSegment(App.Vector(0.069250, -0.000000, 0.000000), App.Vector(0.881071, 0.000000, 0.000000)))
comp.append(Part.LineSegment(App.Vector(0.881071, 0.000000, 0.000000), App.Vector(5.580750, 0.000000, 0.000000)))
comp.append(Part.LineSegment(App.Vector(5.580750, 0.000000, 0.000000), App.Vector(8.280750, 0.000000, 0.000000)))
comp.append(Part.LineSegment(App.Vector(8.280750, 0.000000, 0.000000), App.Vector(8.280750, 5.930750, 0.000000)))
comp.append(Part.LineSegment(App.Vector(8.280750, 5.930750, 0.000000), App.Vector(0.069250, 5.930750, 0.000000)))
comp.append(Part.LineSegment(App.Vector(0.069250, 5.930750, 0.000000), App.Vector(0.069250, 0.000000, 0.000000)))
comp.append(Part.LineSegment(App.Vector(0.000000, 0.000000, 0.000000), App.Vector(6.261490, 0.000000, 0.000000)))
comp.append(Part.LineSegment(App.Vector(6.261490, 0.000000, 0.000000), App.Vector(6.261490, 0.112500, 0.000000)))
comp.append(Part.LineSegment(App.Vector(6.261490, 0.112500, 0.000000), App.Vector(6.864589, 0.112500, 0.000000)))
comp.append(Part.LineSegment(App.Vector(6.864589, 0.112500, 0.000000), App.Vector(6.864589, 5.881900, 0.000000)))
comp.append(Part.LineSegment(App.Vector(6.864589, 5.881900, 0.000000), App.Vector(6.261490, 5.881900, 0.000000)))
comp.append(Part.LineSegment(App.Vector(6.261490, 5.881900, 0.000000), App.Vector(6.261490, 5.994400, 0.000000)))
comp.append(Part.LineSegment(App.Vector(6.261490, 5.994400, 0.000000), App.Vector(0.000000, 5.994400, 0.000000)))
comp.append(Part.LineSegment(App.Vector(0.000000, 5.994400, 0.000000), App.Vector(0.000000, 0.000000, 0.000000)))
comp.append(Part.LineSegment(App.Vector(0.069250, 0.000000, 0.000000), App.Vector(8.280750, -0.000000, 0.000000)))
comp.append(Part.LineSegment(App.Vector(8.280750, -0.000000, 0.000000), App.Vector(8.280750, 3.861500, 0.000000)))
comp.append(Part.LineSegment(App.Vector(8.280750, 3.861500, 0.000000), App.Vector(0.069250, 3.861500, 0.000000)))
comp.append(Part.LineSegment(App.Vector(0.069250, 3.861500, 0.000000), App.Vector(0.069250, 0.000000, 0.000000)))
comp.append(Part.LineSegment(App.Vector(8.211500, 0.000000, 0.000000), App.Vector(8.211500, 7.365750, 0.000000)))
comp.append(Part.LineSegment(App.Vector(8.211500, 7.365750, 0.000000), App.Vector(8.211500, 8.350000, 0.000000)))
comp.append(Part.LineSegment(App.Vector(8.211500, 8.350000, 0.000000), App.Vector(8.211500, 15.472400, 0.000000)))
comp.append(Part.LineSegment(App.Vector(8.211500, 15.472400, 0.000000), App.Vector(0.000000, 15.472400, 0.000000)))
comp.append(Part.LineSegment(App.Vector(0.000000, 15.472400, 0.000000), App.Vector(0.000000, 0.000000, 0.000000)))
comp.append(Part.LineSegment(App.Vector(0.000000, 0.000000, 0.000000), App.Vector(7.265750, 0.000000, 0.000000)))
comp.append(Part.LineSegment(App.Vector(7.265750, 0.000000, 0.000000), App.Vector(7.265750, 2.640000, 0.000000)))
comp.append(Part.LineSegment(App.Vector(7.265750, 2.640000, 0.000000), App.Vector(0.000000, 2.640000, 0.000000)))
comp.append(Part.LineSegment(App.Vector(0.000000, 2.640000, 0.000000), App.Vector(0.000000, 0.000000, 0.000000)))
comp.append(Part.LineSegment(App.Vector(0.000000, 0.000000, 0.000000), App.Vector(3.232781, -0.000000, 0.000000)))
comp.append(Part.LineSegment(App.Vector(3.232781, -0.000000, 0.000000), App.Vector(3.232781, 2.176500, 0.000000)))
comp.append(Part.LineSegment(App.Vector(3.232781, 2.176500, 0.000000), App.Vector(-0.019020, 2.176500, 0.000000)))
comp.append(Part.LineSegment(App.Vector(-0.019020, 2.176500, 0.000000), App.Vector(-0.019020, -0.000000, 0.000000)))
comp.append(Part.LineSegment(App.Vector(-0.019020, -0.000000, 0.000000), App.Vector(0.000000, 0.000000, 0.000000)))
comp.append(Part.LineSegment(App.Vector(0.069250, 0.000000, 0.000000), App.Vector(2.400000, -0.000000, 0.000000)))
comp.append(Part.LineSegment(App.Vector(2.400000, -0.000000, 0.000000), App.Vector(2.400000, 0.845750, 0.000000)))
comp.append(Part.LineSegment(App.Vector(2.400000, 0.845750, 0.000000), App.Vector(2.400000, 8.111500, 0.000000)))
comp.append(Part.LineSegment(App.Vector(2.400000, 8.111500, 0.000000), App.Vector(-3.321051, 8.111500, 0.000000)))
comp.append(Part.LineSegment(App.Vector(-3.321051, 8.111500, 0.000000), App.Vector(-3.321051, 2.315000, 0.000000)))
comp.append(Part.LineSegment(App.Vector(-3.321051, 2.315000, 0.000000), App.Vector(0.069250, 2.315000, 0.000000)))
comp.append(Part.LineSegment(App.Vector(0.069250, 2.315000, 0.000000), App.Vector(0.069250, 0.000000, 0.000000)))
comp.append(Part.LineSegment(App.Vector(0.069250, 0.000000, 0.000000), App.Vector(2.430750, 0.000000, 0.000000)))
comp.append(Part.LineSegment(App.Vector(2.430750, 0.000000, 0.000000), App.Vector(2.430750, 5.796500, 0.000000)))
comp.append(Part.LineSegment(App.Vector(2.430750, 5.796500, 0.000000), App.Vector(1.700000, 5.796500, 0.000000)))
comp.append(Part.LineSegment(App.Vector(1.700000, 5.796500, 0.000000), App.Vector(0.069250, 5.796500, 0.000000)))
comp.append(Part.LineSegment(App.Vector(2.333049, 0.000000, 0.000000), App.Vector(2.333049, 0.516203, 0.000000)))
comp.append(Part.LineSegment(App.Vector(2.333049, 0.516203, 0.000000), App.Vector(2.333049, 0.575997, 0.000000)))
comp.append(Part.LineSegment(App.Vector(2.333049, 0.575997, 0.000000), App.Vector(2.333049, 5.796500, 0.000000)))
comp.append(Part.LineSegment(App.Vector(2.333049, 5.796500, 0.000000), App.Vector(0.702299, 5.796500, 0.000000)))
comp.append(Part.LineSegment(App.Vector(0.702299, 5.796500, 0.000000), App.Vector(0.069250, 5.796500, 0.000000)))
comp.append(Part.LineSegment(App.Vector(0.000000, 0.000000, 0.000000), App.Vector(0.984250, 0.000000, 0.000000)))
comp.append(Part.LineSegment(App.Vector(0.984250, 0.000000, 0.000000), App.Vector(0.984250, -0.100000, 0.000000)))
comp.append(Part.LineSegment(App.Vector(0.984250, -0.100000, 0.000000), App.Vector(3.580050, -0.100000, 0.000000)))
comp.append(Part.LineSegment(App.Vector(3.580050, -0.100000, 0.000000), App.Vector(3.580050, 49.075577, 0.000000)))
comp.append(Part.LineSegment(App.Vector(3.580050, 49.075577, 0.000000), App.Vector(1.068010, 49.075577, 0.000000)))
comp.append(Part.LineSegment(App.Vector(1.068010, 49.075577, 0.000000), App.Vector(0.915000, 49.075577, 0.000000)))
comp.append(Part.LineSegment(App.Vector(0.915000, 49.075577, 0.000000), App.Vector(0.915000, 49.055827, 0.000000)))
comp.append(Part.LineSegment(App.Vector(0.915000, 49.055827, 0.000000), App.Vector(-1.330750, 49.055827, 0.000000)))
comp.append(Part.LineSegment(App.Vector(-1.330750, 49.055827, 0.000000), App.Vector(-1.330750, 47.494327, 0.000000)))
comp.append(Part.LineSegment(App.Vector(-1.330750, 47.494327, 0.000000), App.Vector(0.984250, 47.494327, 0.000000)))
comp.append(Part.LineSegment(App.Vector(0.984250, 47.494327, 0.000000), App.Vector(0.984250, 45.353528, 0.000000)))
comp.append(Part.LineSegment(App.Vector(0.984250, 45.353528, 0.000000), App.Vector(-1.330750, 45.353528, 0.000000)))
comp.append(Part.LineSegment(App.Vector(-1.330750, 45.353528, 0.000000), App.Vector(-1.330750, 43.792028, 0.000000)))
comp.append(Part.LineSegment(App.Vector(-1.330750, 43.792028, 0.000000), App.Vector(0.565653, 43.792028, 0.000000)))
comp.append(Part.LineSegment(App.Vector(0.565653, 43.792028, 0.000000), App.Vector(0.625447, 43.792028, 0.000000)))
comp.append(Part.LineSegment(App.Vector(0.625447, 43.792028, 0.000000), App.Vector(0.984250, 43.792028, 0.000000)))
comp.append(Part.LineSegment(App.Vector(0.984250, 43.792028, 0.000000), App.Vector(0.984250, 32.653528, 0.000000)))
comp.append(Part.LineSegment(App.Vector(0.984250, 32.653528, 0.000000), App.Vector(0.984250, 26.653528, 0.000000)))
comp.append(Part.LineSegment(App.Vector(0.984250, 26.653528, 0.000000), App.Vector(0.984250, 14.653528, 0.000000)))
comp.append(Part.LineSegment(App.Vector(0.984250, 14.653528, 0.000000), App.Vector(0.984250, 8.653528, 0.000000)))
comp.append(Part.LineSegment(App.Vector(0.984250, 8.653528, 0.000000), App.Vector(0.984250, 2.640000, 0.000000)))
comp.append(Part.LineSegment(App.Vector(0.984250, 2.640000, 0.000000), App.Vector(0.000000, 2.640000, 0.000000)))
comp.append(Part.LineSegment(App.Vector(0.000000, 0.000000, 0.000000), App.Vector(0.083760, 0.000000, 0.000000)))
comp.append(Part.LineSegment(App.Vector(0.083760, -0.059794, 0.000000), App.Vector(0.000000, -0.059794, 0.000000)))
comp.append(Part.LineSegment(App.Vector(0.000000, -0.059794, 0.000000), App.Vector(-0.000000, -2.025447, 0.000000)))
comp.append(Part.LineSegment(App.Vector(-0.000000, -2.025447, 0.000000), App.Vector(-0.000000, -7.315200, 0.000000)))
comp.append(Part.LineSegment(App.Vector(-0.000000, -7.315200, 0.000000), App.Vector(0.083760, -7.315200, 0.000000)))
comp.append(Part.LineSegment(App.Vector(0.083760, -7.374994, 0.000000), App.Vector(-0.000000, -7.374994, 0.000000)))
comp.append(Part.LineSegment(App.Vector(-0.000000, -7.374994, 0.000000), App.Vector(-0.000000, -7.991197, 0.000000)))
comp.append(Part.LineSegment(App.Vector(-0.000000, -7.991197, 0.000000), App.Vector(10.930750, -7.991197, 0.000000)))
comp.append(Part.LineSegment(App.Vector(10.930750, -7.991197, 0.000000), App.Vector(10.930750, 0.220303, 0.000000)))
comp.append(Part.LineSegment(App.Vector(10.930750, 0.220303, 0.000000), App.Vector(0.000000, 0.220303, 0.000000)))
comp.append(Part.LineSegment(App.Vector(0.000000, 0.220303, 0.000000), App.Vector(0.000000, 0.000000, 0.000000)))
comp.append(Part.LineSegment(App.Vector(0.069250, 0.000000, 0.000000), App.Vector(5.930750, -0.000000, 0.000000)))
comp.append(Part.LineSegment(App.Vector(5.930750, -0.000000, 0.000000), App.Vector(5.930750, 8.211500, 0.000000)))
comp.append(Part.LineSegment(App.Vector(5.930750, 8.211500, 0.000000), App.Vector(0.069250, 8.211500, 0.000000)))
comp.append(Part.LineSegment(App.Vector(0.069250, 8.211500, 0.000000), App.Vector(0.069250, 0.000000, 0.000000)))
comp.append(Part.LineSegment(App.Vector(0.069250, 0.000000, 0.000000), App.Vector(11.930750, -0.000000, 0.000000)))
comp.append(Part.LineSegment(App.Vector(11.930750, -0.000000, 0.000000), App.Vector(11.930750, 8.211500, 0.000000)))
comp.append(Part.LineSegment(App.Vector(11.930750, 8.211500, 0.000000), App.Vector(0.069250, 8.211500, 0.000000)))
comp.append(Part.LineSegment(App.Vector(0.100000, 0.000000, 0.000000), App.Vector(5.844278, -0.000000, 0.000000)))
comp.append(Part.LineSegment(App.Vector(5.844278, -0.000000, 0.000000), App.Vector(5.844278, 8.211500, 0.000000)))
comp.append(Part.LineSegment(App.Vector(5.844278, 8.211500, 0.000000), App.Vector(0.100000, 8.211500, 0.000000)))
comp.append(Part.LineSegment(App.Vector(0.100000, 8.211500, 0.000000), App.Vector(0.100000, 0.845750, 0.000000)))
comp.append(Part.LineSegment(App.Vector(0.100000, 0.845750, 0.000000), App.Vector(0.100000, 0.000000, 0.000000)))
comp.append(Part.LineSegment(App.Vector(0.151500, 0.000000, 0.000000), App.Vector(7.417250, 0.000000, 0.000000)))
comp.append(Part.LineSegment(App.Vector(7.417250, 0.000000, 0.000000), App.Vector(7.417250, 2.640000, 0.000000)))
comp.append(Part.LineSegment(App.Vector(7.417250, 2.640000, 0.000000), App.Vector(0.151500, 2.640000, 0.000000)))
comp.append(Part.LineSegment(App.Vector(0.151500, 2.640000, 0.000000), App.Vector(0.151500, 0.000000, 0.000000)))
comp.append(Part.LineSegment(App.Vector(0.025000, 0.000000, 0.000000), App.Vector(1.975000, 0.000000, 0.000000)))
comp.append(Part.LineSegment(App.Vector(1.975000, 0.000000, 0.000000), App.Vector(1.975000, 1.215000, 0.000000)))
comp.append(Part.LineSegment(App.Vector(1.975000, 1.215000, 0.000000), App.Vector(0.025000, 1.215000, 0.000000)))
comp.append(Part.LineSegment(App.Vector(0.025000, 1.215000, 0.000000), App.Vector(0.025000, 0.000000, 0.000000)))
comp.append(Part.LineSegment(App.Vector(0.025000, 0.000000, 0.000000), App.Vector(0.671202, 0.000000, 0.000000)))
comp.append(Part.LineSegment(App.Vector(0.671202, 0.000000, 0.000000), App.Vector(0.671202, 1.215000, 0.000000)))
comp.append(Part.LineSegment(App.Vector(0.671202, 1.215000, 0.000000), App.Vector(0.025000, 1.215000, 0.000000)))
comp.append(Part.LineSegment(App.Vector(0.025000, 0.000000, 0.000000), App.Vector(1.489000, 0.000000, 0.000000)))
comp.append(Part.LineSegment(App.Vector(1.489000, 0.000000, 0.000000), App.Vector(1.489000, 1.215000, 0.000000)))
comp.append(Part.LineSegment(App.Vector(1.489000, 1.215000, 0.000000), App.Vector(0.025000, 1.215000, 0.000000)))
comp.append(Part.LineSegment(App.Vector(0.025000, 0.000000, 0.000000), App.Vector(0.545800, 0.000000, 0.000000)))
comp.append(Part.LineSegment(App.Vector(0.545800, 0.000000, 0.000000), App.Vector(0.545800, 1.215000, 0.000000)))
comp.append(Part.LineSegment(App.Vector(0.545800, 1.215000, 0.000000), App.Vector(0.025000, 1.215000, 0.000000)))
comp.append(Part.LineSegment(App.Vector(0.025000, 0.000000, 0.000000), App.Vector(1.488000, 0.000000, 0.000000)))
comp.append(Part.LineSegment(App.Vector(1.488000, 0.000000, 0.000000), App.Vector(1.488000, 1.215000, 0.000000)))
comp.append(Part.LineSegment(App.Vector(1.488000, 1.215000, 0.000000), App.Vector(0.025000, 1.215000, 0.000000)))
comp.append(Part.LineSegment(App.Vector(0.025000, 0.000000, 0.000000), App.Vector(0.590000, 0.000000, 0.000000)))
comp.append(Part.LineSegment(App.Vector(0.590000, 0.000000, 0.000000), App.Vector(0.590000, 1.215000, 0.000000)))
comp.append(Part.LineSegment(App.Vector(0.590000, 1.215000, 0.000000), App.Vector(0.025000, 1.215000, 0.000000)))
comp.append(Part.LineSegment(App.Vector(0.050000, 0.000000, 0.000000), App.Vector(1.975000, 0.000000, 0.000000)))
comp.append(Part.LineSegment(App.Vector(1.975000, 0.000000, 0.000000), App.Vector(1.975000, 1.190000, 0.000000)))
comp.append(Part.LineSegment(App.Vector(1.975000, 1.190000, 0.000000), App.Vector(0.050000, 1.190000, 0.000000)))
comp.append(Part.LineSegment(App.Vector(0.050000, 1.190000, 0.000000), App.Vector(0.050000, 0.000000, 0.000000)))
comp.append(Part.LineSegment(App.Vector(0.025000, 0.000000, 0.000000), App.Vector(1.911352, 0.000000, 0.000000)))
comp.append(Part.LineSegment(App.Vector(1.911352, 0.000000, 0.000000), App.Vector(1.911352, 1.190000, 0.000000)))
comp.append(Part.LineSegment(App.Vector(1.911352, 1.190000, 0.000000), App.Vector(0.025000, 1.190000, 0.000000)))
comp.append(Part.LineSegment(App.Vector(0.025000, 1.190000, 0.000000), App.Vector(0.025000, 0.000000, 0.000000)))
comp.append(Part.LineSegment(App.Vector(0.050000, 0.000000, 0.000000), App.Vector(0.975000, 0.000000, 0.000000)))
comp.append(Part.LineSegment(App.Vector(0.975000, 0.000000, 0.000000), App.Vector(0.975000, 1.190000, 0.000000)))
comp.append(Part.LineSegment(App.Vector(0.975000, 1.190000, 0.000000), App.Vector(0.050000, 1.190000, 0.000000)))
comp.append(Part.LineSegment(App.Vector(0.025000, 0.000000, 0.000000), App.Vector(1.161500, 0.000000, 0.000000)))
comp.append(Part.LineSegment(App.Vector(1.161500, 0.000000, 0.000000), App.Vector(1.161500, 1.190000, 0.000000)))
comp.append(Part.LineSegment(App.Vector(1.161500, 1.190000, 0.000000), App.Vector(0.025000, 1.190000, 0.000000)))
comp.append(Part.LineSegment(App.Vector(0.975000, 0.000000, 0.000000), App.Vector(0.975000, 1.215000, 0.000000)))
comp.append(Part.LineSegment(App.Vector(0.975000, 1.215000, 0.000000), App.Vector(0.050000, 1.215000, 0.000000)))
comp.append(Part.LineSegment(App.Vector(0.050000, 1.215000, 0.000000), App.Vector(0.050000, 0.000000, 0.000000)))
comp.append(Part.LineSegment(App.Vector(1.161500, 0.000000, 0.000000), App.Vector(1.161500, 1.215000, 0.000000)))
comp.append(Part.LineSegment(App.Vector(1.161500, 1.215000, 0.000000), App.Vector(0.025000, 1.215000, 0.000000)))
comp.append(Part.LineSegment(App.Vector(0.025000, 0.000000, 0.000000), App.Vector(1.055750, 0.000000, 0.000000)))
comp.append(Part.LineSegment(App.Vector(1.055750, 0.000000, 0.000000), App.Vector(1.055750, 1.190000, 0.000000)))
comp.append(Part.LineSegment(App.Vector(1.055750, 1.190000, 0.000000), App.Vector(0.025000, 1.190000, 0.000000)))
comp.append(Part.LineSegment(App.Vector(1.055750, 0.000000, 0.000000), App.Vector(1.055750, 1.215000, 0.000000)))
comp.append(Part.LineSegment(App.Vector(1.055750, 1.215000, 0.000000), App.Vector(0.025000, 1.215000, 0.000000)))
comp.append(Part.LineSegment(App.Vector(1.975000, 1.215000, 0.000000), App.Vector(0.050000, 1.215000, 0.000000)))
comp.append(Part.LineSegment(App.Vector(0.025000, 0.000000, 0.000000), App.Vector(1.391650, 0.000000, 0.000000)))
comp.append(Part.LineSegment(App.Vector(1.391650, 0.000000, 0.000000), App.Vector(1.391650, 1.215000, 0.000000)))
comp.append(Part.LineSegment(App.Vector(1.391650, 1.215000, 0.000000), App.Vector(0.025000, 1.215000, 0.000000)))
comp.append(Part.LineSegment(App.Vector(0.025000, 0.000000, 0.000000), App.Vector(1.294900, 0.000000, 0.000000)))
comp.append(Part.LineSegment(App.Vector(1.294900, 0.000000, 0.000000), App.Vector(1.294900, 1.190000, 0.000000)))
comp.append(Part.LineSegment(App.Vector(1.294900, 1.190000, 0.000000), App.Vector(0.025000, 1.190000, 0.000000)))
comp.append(Part.LineSegment(App.Vector(1.294900, 0.000000, 0.000000), App.Vector(1.294900, 1.215000, 0.000000)))
comp.append(Part.LineSegment(App.Vector(1.294900, 1.215000, 0.000000), App.Vector(0.025000, 1.215000, 0.000000)))
comp.append(Part.LineSegment(App.Vector(0.438447, 0.329477, 0.000000), App.Vector(0.431052, 0.329927, 0.000000)))
comp.append(Part.LineSegment(App.Vector(0.431052, 0.329927, 0.000000), App.Vector(0.431052, 0.153715, 0.000000)))
comp.append(Part.LineSegment(App.Vector(0.431052, 0.153715, 0.000000), App.Vector(0.455137, 0.136685, 0.000000)))
comp.append(Part.LineSegment(App.Vector(0.455137, 0.136685, 0.000000), App.Vector(0.451962, 0.134439, 0.000000)))
comp.append(Part.LineSegment(App.Vector(0.451962, 0.134439, 0.000000), App.Vector(0.426562, 0.152400, 0.000000)))
comp.append(Part.LineSegment(App.Vector(0.426562, 0.152400, 0.000000), App.Vector(0.426562, 0.329654, 0.000000)))
comp.append(Part.LineSegment(App.Vector(-0.008980, 0.356146, 0.000000), App.Vector(-0.008980, 0.152400, 0.000000)))
comp.append(Part.LineSegment(App.Vector(-0.008980, 0.152400, 0.000000), App.Vector(-0.034380, 0.134439, 0.000000)))
comp.append(Part.LineSegment(App.Vector(-0.034380, 0.134439, 0.000000), App.Vector(-0.037532, 0.136668, 0.000000)))
comp.append(Part.LineSegment(App.Vector(-0.037532, 0.136668, 0.000000), App.Vector(-0.013470, 0.153682, 0.000000)))
comp.append(Part.LineSegment(App.Vector(-0.013470, 0.153682, 0.000000), App.Vector(-0.013470, 0.369582, 0.000000)))
comp.append(Part.LineSegment(App.Vector(-0.008980, 0.369582, 0.000000), App.Vector(-0.008980, 0.359333, 0.000000)))
comp.append(Part.LineSegment(App.Vector(-0.438447, 0.280123, 0.000000), App.Vector(-0.431052, 0.279673, 0.000000)))
comp.append(Part.LineSegment(App.Vector(-0.431052, 0.279673, 0.000000), App.Vector(-0.431052, 0.455885, 0.000000)))
comp.append(Part.LineSegment(App.Vector(-0.431052, 0.455885, 0.000000), App.Vector(-0.455137, 0.472915, 0.000000)))
comp.append(Part.LineSegment(App.Vector(-0.455137, 0.472915, 0.000000), App.Vector(-0.451962, 0.475161, 0.000000)))
comp.append(Part.LineSegment(App.Vector(-0.451962, 0.475161, 0.000000), App.Vector(-0.426562, 0.457200, 0.000000)))
comp.append(Part.LineSegment(App.Vector(-0.426562, 0.457200, 0.000000), App.Vector(-0.426562, 0.279946, 0.000000)))
comp.append(Part.LineSegment(App.Vector(0.008980, 0.253454, 0.000000), App.Vector(0.008980, 0.457200, 0.000000)))
comp.append(Part.LineSegment(App.Vector(0.008980, 0.457200, 0.000000), App.Vector(0.034380, 0.475161, 0.000000)))
comp.append(Part.LineSegment(App.Vector(0.034380, 0.475161, 0.000000), App.Vector(0.037532, 0.472932, 0.000000)))
comp.append(Part.LineSegment(App.Vector(0.037532, 0.472932, 0.000000), App.Vector(0.013470, 0.455918, 0.000000)))
comp.append(Part.LineSegment(App.Vector(0.013470, 0.455918, 0.000000), App.Vector(0.013470, 0.240018, 0.000000)))
comp.append(Part.LineSegment(App.Vector(0.008980, 0.240018, 0.000000), App.Vector(0.008980, 0.250267, 0.000000)))
comp.append(Part.LineSegment(App.Vector(0.050000, 0.000000, 0.000000), App.Vector(1.336629, 0.000000, 0.000000)))
comp.append(Part.LineSegment(App.Vector(1.336629, 0.000000, 0.000000), App.Vector(1.336629, 2.109000, 0.000000)))
comp.append(Part.LineSegment(App.Vector(1.336629, 2.109000, 0.000000), App.Vector(1.336629, 2.325000, 0.000000)))
comp.append(Part.LineSegment(App.Vector(1.336629, 2.325000, 0.000000), App.Vector(0.050000, 2.325000, 0.000000)))
comp.append(Part.LineSegment(App.Vector(0.050000, 2.325000, 0.000000), App.Vector(0.050000, 2.109000, 0.000000)))
comp.append(Part.LineSegment(App.Vector(0.050000, 2.109000, 0.000000), App.Vector(0.050000, 0.000000, 0.000000)))
comp.append(Part.LineSegment(App.Vector(0.025000, 0.000000, 0.000000), App.Vector(1.336629, 0.000000, 0.000000)))
comp.append(Part.LineSegment(App.Vector(1.336629, 2.325000, 0.000000), App.Vector(0.025000, 2.325000, 0.000000)))
comp.append(Part.LineSegment(App.Vector(0.025000, 2.325000, 0.000000), App.Vector(0.025000, 2.109000, 0.000000)))
comp.append(Part.LineSegment(App.Vector(0.025000, 2.109000, 0.000000), App.Vector(0.025000, 0.000000, 0.000000)))
comp.append(Part.LineSegment(App.Vector(0.025000, 0.000000, 0.000000), App.Vector(0.396629, 0.000000, 0.000000)))
comp.append(Part.LineSegment(App.Vector(0.396629, 0.000000, 0.000000), App.Vector(0.396629, 2.109000, 0.000000)))
comp.append(Part.LineSegment(App.Vector(0.396629, 2.109000, 0.000000), App.Vector(0.396629, 2.325000, 0.000000)))
comp.append(Part.LineSegment(App.Vector(0.396629, 2.325000, 0.000000), App.Vector(0.025000, 2.325000, 0.000000)))
comp.append(Part.LineSegment(App.Vector(0.025000, 0.000000, 0.000000), App.Vector(0.940000, 0.000000, 0.000000)))
comp.append(Part.LineSegment(App.Vector(0.940000, 0.000000, 0.000000), App.Vector(1.855000, 0.000000, 0.000000)))
comp.append(Part.LineSegment(App.Vector(1.855000, 0.000000, 0.000000), App.Vector(1.855000, 0.191000, 0.000000)))
comp.append(Part.LineSegment(App.Vector(1.855000, 0.191000, 0.000000), App.Vector(0.940000, 0.191000, 0.000000)))
comp.append(Part.LineSegment(App.Vector(0.940000, 0.191000, 0.000000), App.Vector(0.025000, 0.191000, 0.000000)))
comp.append(Part.LineSegment(App.Vector(0.025000, 0.191000, 0.000000), App.Vector(0.025000, 0.000000, 0.000000)))
comp.append(Part.LineSegment(App.Vector(1.911352, 0.000000, 0.000000), App.Vector(1.911352, 0.869000, 0.000000)))
comp.append(Part.LineSegment(App.Vector(1.911352, 0.869000, 0.000000), App.Vector(1.911352, 1.215000, 0.000000)))
comp.append(Part.LineSegment(App.Vector(1.911352, 1.215000, 0.000000), App.Vector(0.025000, 1.215000, 0.000000)))
comp.append(Part.LineSegment(App.Vector(0.025000, 1.215000, 0.000000), App.Vector(0.025000, 0.869000, 0.000000)))
comp.append(Part.LineSegment(App.Vector(0.025000, 0.869000, 0.000000), App.Vector(0.025000, 0.000000, 0.000000)))
comp.append(Part.LineSegment(App.Vector(1.975000, 0.000000, 0.000000), App.Vector(1.975000, 0.869000, 0.000000)))
comp.append(Part.LineSegment(App.Vector(1.975000, 0.869000, 0.000000), App.Vector(1.975000, 1.215000, 0.000000)))
comp.append(Part.LineSegment(App.Vector(0.050000, 1.215000, 0.000000), App.Vector(0.050000, 0.869000, 0.000000)))
comp.append(Part.LineSegment(App.Vector(0.050000, 0.869000, 0.000000), App.Vector(0.050000, 0.000000, 0.000000)))
comp.append(Part.LineSegment(App.Vector(0.025000, 0.000000, 0.000000), App.Vector(0.095000, 0.000000, 0.000000)))
comp.append(Part.LineSegment(App.Vector(0.095000, 0.000000, 0.000000), App.Vector(0.095000, 1.215000, 0.000000)))
comp.append(Part.LineSegment(App.Vector(0.095000, 1.215000, 0.000000), App.Vector(0.095000, 2.084000, 0.000000)))
comp.append(Part.LineSegment(App.Vector(0.095000, 2.084000, 0.000000), App.Vector(0.025000, 2.084000, 0.000000)))
comp.append(Part.LineSegment(App.Vector(0.025000, 2.084000, 0.000000), App.Vector(0.025000, 1.215000, 0.000000)))
comp.append(Part.LineSegment(App.Vector(0.095000, 0.000000, 0.000000), App.Vector(0.095000, 1.265000, 0.000000)))
comp.append(Part.LineSegment(App.Vector(0.095000, 1.265000, 0.000000), App.Vector(0.095000, 2.134000, 0.000000)))
comp.append(Part.LineSegment(App.Vector(0.095000, 2.134000, 0.000000), App.Vector(0.025000, 2.134000, 0.000000)))
comp.append(Part.LineSegment(App.Vector(0.025000, 2.134000, 0.000000), App.Vector(0.025000, 1.265000, 0.000000)))
comp.append(Part.LineSegment(App.Vector(0.025000, 1.265000, 0.000000), App.Vector(0.025000, 0.000000, 0.000000)))
comp.append(Part.LineSegment(App.Vector(0.025000, 0.000000, 0.000000), App.Vector(1.880000, 0.000000, 0.000000)))
comp.append(Part.LineSegment(App.Vector(1.880000, 0.000000, 0.000000), App.Vector(1.975000, 0.000000, 0.000000)))
comp.append(Part.LineSegment(App.Vector(1.975000, 0.000000, 0.000000), App.Vector(1.975000, 0.321000, 0.000000)))
comp.append(Part.LineSegment(App.Vector(1.975000, 0.321000, 0.000000), App.Vector(1.880000, 0.321000, 0.000000)))
comp.append(Part.LineSegment(App.Vector(1.880000, 0.321000, 0.000000), App.Vector(0.025000, 0.321000, 0.000000)))
comp.append(Part.LineSegment(App.Vector(0.025000, 0.321000, 0.000000), App.Vector(0.025000, 0.000000, 0.000000)))
comp.append(Part.LineSegment(App.Vector(0.025000, 0.000000, 0.000000), App.Vector(0.120000, 0.000000, 0.000000)))
comp.append(Part.LineSegment(App.Vector(0.120000, 0.000000, 0.000000), App.Vector(1.975000, 0.000000, 0.000000)))
comp.append(Part.LineSegment(App.Vector(1.975000, 0.321000, 0.000000), App.Vector(0.120000, 0.321000, 0.000000)))
comp.append(Part.LineSegment(App.Vector(0.120000, 0.321000, 0.000000), App.Vector(0.025000, 0.321000, 0.000000)))
comp.append(Part.LineSegment(App.Vector(0.050000, 0.000000, 0.000000), App.Vector(1.681800, 0.000000, 0.000000)))
comp.append(Part.LineSegment(App.Vector(1.681800, 0.000000, 0.000000), App.Vector(1.681800, 1.190000, 0.000000)))
comp.append(Part.LineSegment(App.Vector(1.681800, 1.190000, 0.000000), App.Vector(0.050000, 1.190000, 0.000000)))
comp.append(Part.LineSegment(App.Vector(1.681800, 0.000000, 0.000000), App.Vector(1.681800, 1.215000, 0.000000)))
comp.append(Part.LineSegment(App.Vector(1.681800, 1.215000, 0.000000), App.Vector(0.050000, 1.215000, 0.000000)))
comp.append(Part.LineSegment(App.Vector(0.025000, 0.000000, 0.000000), App.Vector(0.965899, 0.000000, 0.000000)))
comp.append(Part.LineSegment(App.Vector(0.965899, 0.000000, 0.000000), App.Vector(0.965899, 1.190000, 0.000000)))
comp.append(Part.LineSegment(App.Vector(0.965899, 1.190000, 0.000000), App.Vector(0.025000, 1.190000, 0.000000)))
comp.append(Part.LineSegment(App.Vector(0.965899, 0.000000, 0.000000), App.Vector(0.965899, 1.215000, 0.000000)))
comp.append(Part.LineSegment(App.Vector(0.965899, 1.215000, 0.000000), App.Vector(0.025000, 1.215000, 0.000000)))
comp.append(Part.LineSegment(App.Vector(0.150000, 0.000000, 0.000000), App.Vector(1.975000, 0.000000, 0.000000)))
comp.append(Part.LineSegment(App.Vector(1.975000, 1.190000, 0.000000), App.Vector(0.150000, 1.190000, 0.000000)))
comp.append(Part.LineSegment(App.Vector(0.150000, 1.190000, 0.000000), App.Vector(0.150000, 0.000000, 0.000000)))
comp.append(Part.LineSegment(App.Vector(1.975000, 1.215000, 0.000000), App.Vector(0.150000, 1.215000, 0.000000)))
comp.append(Part.LineSegment(App.Vector(0.150000, 1.215000, 0.000000), App.Vector(0.150000, 0.000000, 0.000000)))
comp.append(Part.LineSegment(App.Vector(0.025000, 0.000000, 0.000000), App.Vector(1.075077, 0.000000, 0.000000)))
comp.append(Part.LineSegment(App.Vector(1.075077, 0.000000, 0.000000), App.Vector(1.075077, 1.190000, 0.000000)))
comp.append(Part.LineSegment(App.Vector(1.075077, 1.190000, 0.000000), App.Vector(0.025000, 1.190000, 0.000000)))
comp.append(Part.LineSegment(App.Vector(1.075077, 0.000000, 0.000000), App.Vector(1.075077, 1.215000, 0.000000)))
comp.append(Part.LineSegment(App.Vector(1.075077, 1.215000, 0.000000), App.Vector(0.025000, 1.215000, 0.000000)))
comp.append(Part.LineSegment(App.Vector(0.025000, 0.000000, 0.000000), App.Vector(2.415000, 0.000000, 0.000000)))
comp.append(Part.LineSegment(App.Vector(2.415000, 0.000000, 0.000000), App.Vector(2.415000, 0.535000, 0.000000)))
comp.append(Part.LineSegment(App.Vector(2.415000, 0.535000, 0.000000), App.Vector(0.025000, 0.535000, 0.000000)))
comp.append(Part.LineSegment(App.Vector(0.025000, 0.535000, 0.000000), App.Vector(0.025000, 0.000000, 0.000000)))
comp.append(Part.LineSegment(App.Vector(2.415000, 0.000000, 0.000000), App.Vector(2.415000, 0.560000, 0.000000)))
comp.append(Part.LineSegment(App.Vector(2.415000, 0.560000, 0.000000), App.Vector(0.025000, 0.560000, 0.000000)))
comp.append(Part.LineSegment(App.Vector(0.025000, 0.560000, 0.000000), App.Vector(0.025000, 0.000000, 0.000000)))
comp.append(Part.LineSegment(App.Vector(0.050000, 0.000000, 0.000000), App.Vector(0.665745, 0.000000, 0.000000)))
comp.append(Part.LineSegment(App.Vector(0.665745, 0.000000, 0.000000), App.Vector(0.665745, 0.535000, 0.000000)))
comp.append(Part.LineSegment(App.Vector(0.665745, 0.535000, 0.000000), App.Vector(0.050000, 0.535000, 0.000000)))
comp.append(Part.LineSegment(App.Vector(0.050000, 0.535000, 0.000000), App.Vector(0.050000, 0.000000, 0.000000)))
comp.append(Part.LineSegment(App.Vector(0.665745, -0.000000, 0.000000), App.Vector(0.665745, 0.560000, 0.000000)))
comp.append(Part.LineSegment(App.Vector(0.665745, 0.560000, 0.000000), App.Vector(0.050000, 0.560000, 0.000000)))
comp.append(Part.LineSegment(App.Vector(0.050000, 0.560000, 0.000000), App.Vector(0.050000, 0.000000, 0.000000)))
comp.append(Part.LineSegment(App.Vector(0.025000, 0.000000, 0.000000), App.Vector(0.407200, 0.000000, 0.000000)))
comp.append(Part.LineSegment(App.Vector(0.407200, 0.000000, 0.000000), App.Vector(0.407200, 0.535000, 0.000000)))
comp.append(Part.LineSegment(App.Vector(0.407200, 0.535000, 0.000000), App.Vector(0.025000, 0.535000, 0.000000)))
comp.append(Part.LineSegment(App.Vector(0.407200, 0.000000, 0.000000), App.Vector(0.407200, 0.560000, 0.000000)))
comp.append(Part.LineSegment(App.Vector(0.407200, 0.560000, 0.000000), App.Vector(0.025000, 0.560000, 0.000000)))
comp.append(Part.LineSegment(App.Vector(0.150000, 0.000000, 0.000000), App.Vector(0.665745, 0.000000, 0.000000)))
comp.append(Part.LineSegment(App.Vector(0.665745, 0.535000, 0.000000), App.Vector(0.150000, 0.535000, 0.000000)))
comp.append(Part.LineSegment(App.Vector(0.150000, 0.535000, 0.000000), App.Vector(0.150000, 0.000000, 0.000000)))
comp.append(Part.LineSegment(App.Vector(0.665745, 0.560000, 0.000000), App.Vector(0.150000, 0.560000, 0.000000)))
comp.append(Part.LineSegment(App.Vector(0.150000, 0.560000, 0.000000), App.Vector(0.150000, 0.000000, 0.000000)))
comp.append(Part.LineSegment(App.Vector(0.665745, 0.000000, 0.000000), App.Vector(0.665745, 0.304000, 0.000000)))
comp.append(Part.LineSegment(App.Vector(0.665745, 0.304000, 0.000000), App.Vector(0.665745, 0.560000, 0.000000)))
comp.append(Part.LineSegment(App.Vector(0.150000, 0.560000, 0.000000), App.Vector(0.150000, 0.304000, 0.000000)))
comp.append(Part.LineSegment(App.Vector(0.150000, 0.304000, 0.000000), App.Vector(0.150000, 0.000000, 0.000000)))
comp.append(Part.LineSegment(App.Vector(-33.300130, 0.000000, 0.000000), App.Vector(4.801470, 0.000000, 0.000000)))
comp.append(Part.LineSegment(App.Vector(4.801470, 0.000000, 0.000000), App.Vector(4.801470, 0.950000, 0.000000)))
comp.append(Part.LineSegment(App.Vector(4.801470, 0.950000, 0.000000), App.Vector(-33.300130, 0.950000, 0.000000)))
comp.append(Part.LineSegment(App.Vector(-33.300130, 0.950000, 0.000000), App.Vector(-33.300130, 0.000000, 0.000000)))
comp.append(Part.LineSegment(App.Vector(-19.886780, 0.000000, 0.000000), App.Vector(-13.785180, 0.000000, 0.000000)))
comp.append(Part.LineSegment(App.Vector(-13.785180, 0.000000, 0.000000), App.Vector(-13.785180, 0.950000, 0.000000)))
comp.append(Part.LineSegment(App.Vector(-13.785180, 0.950000, 0.000000), App.Vector(-19.886780, 0.950000, 0.000000)))
comp.append(Part.LineSegment(App.Vector(-19.886780, 0.950000, 0.000000), App.Vector(-19.886780, 0.000000, 0.000000)))
comp.append(Part.LineSegment(App.Vector(-19.886780, 0.000000, 0.000000), App.Vector(2.214820, 0.000000, 0.000000)))
comp.append(Part.LineSegment(App.Vector(2.214820, 0.000000, 0.000000), App.Vector(2.214820, 0.950000, 0.000000)))
comp.append(Part.LineSegment(App.Vector(2.214820, 0.950000, 0.000000), App.Vector(-19.886780, 0.950000, 0.000000)))
comp.append(Part.LineSegment(App.Vector(-10.558228, -0.000000, 0.000000), App.Vector(-4.456628, -0.000000, 0.000000)))
comp.append(Part.LineSegment(App.Vector(-4.456628, -0.000000, 0.000000), App.Vector(-4.456628, 0.950000, 0.000000)))
comp.append(Part.LineSegment(App.Vector(-4.456628, 0.950000, 0.000000), App.Vector(-10.558228, 0.950000, 0.000000)))
comp.append(Part.LineSegment(App.Vector(-10.558228, 0.950000, 0.000000), App.Vector(-10.558228, -0.000000, 0.000000)))
comp.append(Part.LineSegment(App.Vector(0.590000, 0.000000, 0.000000), App.Vector(0.590000, 1.190000, 0.000000)))
comp.append(Part.LineSegment(App.Vector(0.590000, 1.190000, 0.000000), App.Vector(0.025000, 1.190000, 0.000000)))
comp.append(Part.LineSegment(App.Vector(-54.076202, 0.000000, 0.000000), App.Vector(0.000000, 0.000000, 0.000000)))
comp.append(Part.LineSegment(App.Vector(-0.000000, 0.000000, 0.000000), App.Vector(-0.000000, 37.312199, 0.000000)))
comp.append(Part.LineSegment(App.Vector(-0.000000, 37.312199, 0.000000), App.Vector(-11.277202, 37.312199, 0.000000)))
comp.append(Part.LineSegment(App.Vector(-11.277202, 37.312199, 0.000000), App.Vector(-11.277202, 17.347801, 0.000000)))
comp.append(Part.LineSegment(App.Vector(-11.277202, 17.347801, 0.000000), App.Vector(-31.178502, 17.347801, 0.000000)))
comp.append(Part.LineSegment(App.Vector(-31.178502, 17.347801, 0.000000), App.Vector(-31.178502, 24.212390, 0.000000)))
comp.append(Part.LineSegment(App.Vector(-31.178502, 24.212390, 0.000000), App.Vector(-37.578902, 24.212390, 0.000000)))
comp.append(Part.LineSegment(App.Vector(-37.578902, 24.212390, 0.000000), App.Vector(-37.578902, 17.347801, 0.000000)))
comp.append(Part.LineSegment(App.Vector(-37.578902, 17.347801, 0.000000), App.Vector(-42.824402, 17.347801, 0.000000)))
comp.append(Part.LineSegment(App.Vector(-42.824402, 17.347801, 0.000000), App.Vector(-42.824402, 66.472878, 0.000000)))
comp.append(Part.LineSegment(App.Vector(-42.824402, 66.472878, 0.000000), App.Vector(-54.076202, 66.472878, 0.000000)))
comp.append(Part.LineSegment(App.Vector(-54.076202, 66.472878, 0.000000), App.Vector(-54.076202, 0.000000, 0.000000)))
comp.append(Part.LineSegment(App.Vector(0.000000, 0.000000, 0.000000), App.Vector(7.365750, 0.000000, 0.000000)))
comp.append(Part.LineSegment(App.Vector(7.365750, 0.000000, 0.000000), App.Vector(7.365750, 2.640000, 0.000000)))
comp.append(Part.LineSegment(App.Vector(7.365750, 2.640000, 0.000000), App.Vector(0.000000, 2.640000, 0.000000)))
comp.append(Part.LineSegment(App.Vector(-0.083760, 0.000000, 0.000000), App.Vector(3.660518, 0.000000, 0.000000)))
comp.append(Part.LineSegment(App.Vector(3.660518, 0.000000, 0.000000), App.Vector(3.660518, 7.365750, 0.000000)))
comp.append(Part.LineSegment(App.Vector(3.660518, 7.365750, 0.000000), App.Vector(3.660518, 8.211500, 0.000000)))
comp.append(Part.LineSegment(App.Vector(3.660518, 8.211500, 0.000000), App.Vector(-0.083760, 8.211500, 0.000000)))
comp.append(Part.LineSegment(App.Vector(-0.083760, 8.211500, 0.000000), App.Vector(-0.083760, 0.000000, 0.000000)))
comp.append(Part.LineSegment(App.Vector(-0.083760, 0.000000, 0.000000), App.Vector(3.777740, 0.000000, 0.000000)))
comp.append(Part.LineSegment(App.Vector(3.777740, 0.000000, 0.000000), App.Vector(3.777740, 8.211500, 0.000000)))
comp.append(Part.LineSegment(App.Vector(3.777740, 8.211500, 0.000000), App.Vector(-0.083760, 8.211500, 0.000000)))
comp.append(Part.LineSegment(App.Vector(-0.083760, 8.211500, 0.000000), App.Vector(-0.083760, 8.069161, 0.000000)))
comp.append(Part.LineSegment(App.Vector(-0.083760, 8.069161, 0.000000), App.Vector(-0.083760, 7.853439, 0.000000)))
comp.append(Part.LineSegment(App.Vector(-0.083760, 7.853439, 0.000000), App.Vector(-0.083760, 0.753961, 0.000000)))
comp.append(Part.LineSegment(App.Vector(-0.083760, 0.753961, 0.000000), App.Vector(-0.083760, 0.538239, 0.000000)))
comp.append(Part.LineSegment(App.Vector(-0.083760, 0.538239, 0.000000), App.Vector(-0.083760, 0.000000, 0.000000)))
comp.append(Part.LineSegment(App.Vector(0.107861, -0.254240, 0.000000), App.Vector(0.107861, -0.338000, 0.000000)))
comp.append(Part.LineSegment(App.Vector(0.107861, -0.338000, 0.000000), App.Vector(0.250200, -0.338000, 0.000000)))
comp.append(Part.LineSegment(App.Vector(0.250200, -0.338000, 0.000000), App.Vector(0.250200, 5.523500, 0.000000)))
comp.append(Part.LineSegment(App.Vector(0.250200, 5.523500, 0.000000), App.Vector(-7.961300, 5.523500, 0.000000)))
comp.append(Part.LineSegment(App.Vector(-7.961300, 5.523500, 0.000000), App.Vector(-7.961300, -0.338000, 0.000000)))
comp.append(Part.LineSegment(App.Vector(-7.961300, -0.338000, 0.000000), App.Vector(-7.423061, -0.338000, 0.000000)))
comp.append(Part.LineSegment(App.Vector(-7.423061, -0.338000, 0.000000), App.Vector(-7.423061, -0.254240, 0.000000)))
comp.append(Part.LineSegment(App.Vector(-7.207339, -0.254240, 0.000000), App.Vector(-7.207339, -0.338000, 0.000000)))
comp.append(Part.LineSegment(App.Vector(-7.207339, -0.338000, 0.000000), App.Vector(-0.107861, -0.338000, 0.000000)))
comp.append(Part.LineSegment(App.Vector(-0.107861, -0.338000, 0.000000), App.Vector(-0.107861, -0.254240, 0.000000)))
comp.append(Part.LineSegment(App.Vector(3.580050, -0.100000, 0.000000), App.Vector(3.580050, 49.125077, 0.000000)))
comp.append(Part.LineSegment(App.Vector(3.580050, 49.125077, 0.000000), App.Vector(0.915000, 49.125077, 0.000000)))
comp.append(Part.LineSegment(App.Vector(0.915000, 49.125077, 0.000000), App.Vector(0.915000, 49.055827, 0.000000)))
comp.append(Part.LineSegment(App.Vector(0.984250, 43.792028, 0.000000), App.Vector(0.984250, 34.653528, 0.000000)))
comp.append(Part.LineSegment(App.Vector(0.984250, 34.653528, 0.000000), App.Vector(0.984250, 28.653528, 0.000000)))
comp.append(Part.LineSegment(App.Vector(0.984250, 28.653528, 0.000000), App.Vector(0.984250, 24.653528, 0.000000)))
comp.append(Part.LineSegment(App.Vector(0.984250, 24.653528, 0.000000), App.Vector(0.984250, 20.653528, 0.000000)))
comp.append(Part.LineSegment(App.Vector(0.984250, 20.653528, 0.000000), App.Vector(0.984250, 16.653528, 0.000000)))
comp.append(Part.LineSegment(App.Vector(0.984250, 16.653528, 0.000000), App.Vector(0.984250, 10.653528, 0.000000)))
comp.append(Part.LineSegment(App.Vector(0.984250, 10.653528, 0.000000), App.Vector(0.984250, 6.653528, 0.000000)))
comp.append(Part.LineSegment(App.Vector(0.984250, 6.653528, 0.000000), App.Vector(0.984250, 2.640000, 0.000000)))
comp.append(Part.LineSegment(App.Vector(0.000000, 0.000000, 0.000000), App.Vector(5.539000, 0.000000, 0.000000)))
comp.append(Part.LineSegment(App.Vector(5.539000, 0.000000, 0.000000), App.Vector(5.539000, 0.796901, 0.000000)))
comp.append(Part.LineSegment(App.Vector(5.539000, 0.796901, 0.000000), App.Vector(5.764000, 0.796901, 0.000000)))
comp.append(Part.LineSegment(App.Vector(5.764000, 0.796901, 0.000000), App.Vector(5.764000, 0.000000, 0.000000)))
comp.append(Part.LineSegment(App.Vector(5.764000, 0.000000, 0.000000), App.Vector(11.533401, 0.000000, 0.000000)))
comp.append(Part.LineSegment(App.Vector(11.533401, 0.000000, 0.000000), App.Vector(11.533401, 0.796901, 0.000000)))
comp.append(Part.LineSegment(App.Vector(11.533401, 0.796901, 0.000000), App.Vector(11.758401, 0.796901, 0.000000)))
comp.append(Part.LineSegment(App.Vector(11.758401, 0.796901, 0.000000), App.Vector(11.758401, 0.000000, 0.000000)))
comp.append(Part.LineSegment(App.Vector(11.758401, 0.000000, 0.000000), App.Vector(22.133401, 0.000000, 0.000000)))
comp.append(Part.LineSegment(App.Vector(22.133401, 0.000000, 0.000000), App.Vector(22.133401, 0.796901, 0.000000)))
comp.append(Part.LineSegment(App.Vector(22.133401, 0.796901, 0.000000), App.Vector(22.358401, 0.796901, 0.000000)))
comp.append(Part.LineSegment(App.Vector(22.358401, 0.796901, 0.000000), App.Vector(22.358401, 0.000000, 0.000000)))
comp.append(Part.LineSegment(App.Vector(22.358401, 0.000000, 0.000000), App.Vector(29.896401, 0.000000, 0.000000)))
comp.append(Part.LineSegment(App.Vector(29.896401, 0.000000, 0.000000), App.Vector(29.896401, 0.796901, 0.000000)))
comp.append(Part.LineSegment(App.Vector(29.896401, 0.796901, 0.000000), App.Vector(30.008901, 0.796901, 0.000000)))
comp.append(Part.LineSegment(App.Vector(30.008901, 0.796901, 0.000000), App.Vector(30.008901, 8.691801, 0.000000)))
comp.append(Part.LineSegment(App.Vector(30.008901, 8.691801, 0.000000), App.Vector(22.965100, 8.691801, 0.000000)))
comp.append(Part.LineSegment(App.Vector(22.965100, 8.691801, 0.000000), App.Vector(17.765100, 8.691801, 0.000000)))
comp.append(Part.LineSegment(App.Vector(17.765100, 8.691801, 0.000000), App.Vector(14.665100, 8.691801, 0.000000)))
comp.append(Part.LineSegment(App.Vector(14.665100, 8.691801, 0.000000), App.Vector(0.595850, 8.691801, 0.000000)))
comp.append(Part.LineSegment(App.Vector(0.595850, 8.691801, 0.000000), App.Vector(-2.595800, 8.691801, 0.000000)))
comp.append(Part.LineSegment(App.Vector(-2.595800, 8.691801, 0.000000), App.Vector(-2.595800, 8.630301, 0.000000)))
comp.append(Part.LineSegment(App.Vector(-2.595800, 8.630301, 0.000000), App.Vector(-3.580050, 8.630301, 0.000000)))
comp.append(Part.LineSegment(App.Vector(-3.580050, 8.630301, 0.000000), App.Vector(-3.580050, 5.990301, 0.000000)))
comp.append(Part.LineSegment(App.Vector(-3.580050, 5.990301, 0.000000), App.Vector(-2.595800, 5.990301, 0.000000)))
comp.append(Part.LineSegment(App.Vector(-2.595800, 5.990301, 0.000000), App.Vector(-2.595800, 3.390301, 0.000000)))
comp.append(Part.LineSegment(App.Vector(-2.595800, 3.390301, 0.000000), App.Vector(-2.595800, 0.000000, 0.000000)))
comp.append(Part.LineSegment(App.Vector(-2.595800, 0.000000, 0.000000), App.Vector(0.000000, 0.000000, 0.000000)))
comp.append(Part.LineSegment(App.Vector(8.211500, 8.350000, 0.000000), App.Vector(8.211500, 11.472400, 0.000000)))
comp.append(Part.LineSegment(App.Vector(8.211500, 11.472400, 0.000000), App.Vector(0.000000, 11.472400, 0.000000)))
comp.append(Part.LineSegment(App.Vector(0.000000, 11.472400, 0.000000), App.Vector(0.000000, 0.000000, 0.000000)))
comp.append(Part.LineSegment(App.Vector(0.069250, 0.000000, 0.000000), App.Vector(3.100000, 0.000000, 0.000000)))
comp.append(Part.LineSegment(App.Vector(3.100000, 0.000000, 0.000000), App.Vector(3.100000, -0.100000, 0.000000)))
comp.append(Part.LineSegment(App.Vector(3.100000, -0.100000, 0.000000), App.Vector(17.100000, -0.100000, 0.000000)))
comp.append(Part.LineSegment(App.Vector(17.100000, -0.100000, 0.000000), App.Vector(17.100000, 8.111500, 0.000000)))
comp.append(Part.LineSegment(App.Vector(17.100000, 8.111500, 0.000000), App.Vector(3.169250, 8.111500, 0.000000)))
comp.append(Part.LineSegment(App.Vector(3.169250, 8.111500, 0.000000), App.Vector(3.169250, 2.611500, 0.000000)))
comp.append(Part.LineSegment(App.Vector(3.169250, 2.611500, 0.000000), App.Vector(0.069250, 2.611500, 0.000000)))
comp.append(Part.LineSegment(App.Vector(0.069250, 2.611500, 0.000000), App.Vector(0.069250, 0.000000, 0.000000)))
comp.append(Part.LineSegment(App.Vector(0.069250, -0.000000, 0.000000), App.Vector(5.430750, 0.000000, 0.000000)))
comp.append(Part.LineSegment(App.Vector(5.430750, 0.000000, 0.000000), App.Vector(5.430750, 2.961500, 0.000000)))
comp.append(Part.LineSegment(App.Vector(5.430750, 2.961500, 0.000000), App.Vector(0.069250, 2.961500, 0.000000)))
comp.append(Part.LineSegment(App.Vector(0.069250, 2.961500, 0.000000), App.Vector(0.069250, 0.000000, 0.000000)))
comp.append(Part.LineSegment(App.Vector(0.069250, 0.000000, 0.000000), App.Vector(5.130750, 0.000000, 0.000000)))
comp.append(Part.LineSegment(App.Vector(5.130750, 0.000000, 0.000000), App.Vector(5.130750, 2.680750, 0.000000)))
comp.append(Part.LineSegment(App.Vector(5.130750, 2.680750, 0.000000), App.Vector(5.130750, 8.111500, 0.000000)))
comp.append(Part.LineSegment(App.Vector(5.130750, 8.111500, 0.000000), App.Vector(0.069250, 8.111500, 0.000000)))
comp.append(Part.LineSegment(App.Vector(0.069250, 8.111500, 0.000000), App.Vector(0.069250, 0.000000, 0.000000)))
comp.append(Part.LineSegment(App.Vector(0.069250, 0.000000, 0.000000), App.Vector(3.174551, 0.000000, 0.000000)))
comp.append(Part.LineSegment(App.Vector(3.174551, 0.000000, 0.000000), App.Vector(3.174551, 5.600000, 0.000000)))
comp.append(Part.LineSegment(App.Vector(3.174551, 5.600000, 0.000000), App.Vector(3.313051, 5.600000, 0.000000)))
comp.append(Part.LineSegment(App.Vector(3.313051, 5.600000, 0.000000), App.Vector(3.313051, 0.000000, 0.000000)))
comp.append(Part.LineSegment(App.Vector(3.313051, 0.000000, 0.000000), App.Vector(6.974551, 0.000000, 0.000000)))
comp.append(Part.LineSegment(App.Vector(6.974551, 0.000000, 0.000000), App.Vector(6.974551, 8.111500, 0.000000)))
comp.append(Part.LineSegment(App.Vector(6.974551, 8.111500, 0.000000), App.Vector(0.069250, 8.111500, 0.000000)))
comp.append(Part.LineSegment(App.Vector(0.000000, 0.000000, 0.000000), App.Vector(8.257250, 0.000000, 0.000000)))
comp.append(Part.LineSegment(App.Vector(8.257250, 0.000000, 0.000000), App.Vector(8.257250, 0.100000, 0.000000)))
comp.append(Part.LineSegment(App.Vector(8.257250, 0.100000, 0.000000), App.Vector(12.846252, 0.100000, 0.000000)))
comp.append(Part.LineSegment(App.Vector(12.846252, 0.100000, 0.000000), App.Vector(12.846252, 8.280750, 0.000000)))
comp.append(Part.LineSegment(App.Vector(12.846252, 8.280750, 0.000000), App.Vector(8.180750, 8.280750, 0.000000)))
comp.append(Part.LineSegment(App.Vector(8.180750, 8.280750, 0.000000), App.Vector(8.180750, 10.481747, 0.000000)))
comp.append(Part.LineSegment(App.Vector(8.180750, 10.481747, 0.000000), App.Vector(8.042980, 10.481747, 0.000000)))
comp.append(Part.LineSegment(App.Vector(8.042980, 10.622453, 0.000000), App.Vector(8.180750, 10.622453, 0.000000)))
comp.append(Part.LineSegment(App.Vector(8.180750, 10.622453, 0.000000), App.Vector(8.180750, 11.672551, 0.000000)))
comp.append(Part.LineSegment(App.Vector(8.180750, 11.672551, 0.000000), App.Vector(2.280750, 11.672551, 0.000000)))
comp.append(Part.LineSegment(App.Vector(2.280750, 11.672551, 0.000000), App.Vector(2.280750, 11.741801, 0.000000)))
comp.append(Part.LineSegment(App.Vector(2.280750, 11.741801, 0.000000), App.Vector(0.000000, 11.741801, 0.000000)))
comp.append(Part.LineSegment(App.Vector(0.000000, 11.741801, 0.000000), App.Vector(0.000000, 0.000000, 0.000000)))
comp.append(Part.LineSegment(App.Vector(0.069250, 0.000000, 0.000000), App.Vector(1.765000, 0.000000, 0.000000)))
comp.append(Part.LineSegment(App.Vector(1.765000, 0.000000, 0.000000), App.Vector(1.765000, -0.100000, 0.000000)))
comp.append(Part.LineSegment(App.Vector(1.765000, -0.100000, 0.000000), App.Vector(6.468099, -0.100000, 0.000000)))
comp.append(Part.LineSegment(App.Vector(6.468099, -0.100000, 0.000000), App.Vector(6.468099, 2.180750, 0.000000)))
comp.append(Part.LineSegment(App.Vector(6.468099, 2.180750, 0.000000), App.Vector(6.398849, 2.180750, 0.000000)))
comp.append(Part.LineSegment(App.Vector(6.398849, 2.180750, 0.000000), App.Vector(6.398849, 8.011500, 0.000000)))
comp.append(Part.LineSegment(App.Vector(6.398849, 8.011500, 0.000000), App.Vector(3.737349, 8.011500, 0.000000)))
comp.append(Part.LineSegment(App.Vector(3.737349, 8.011500, 0.000000), App.Vector(3.737349, 5.880750, 0.000000)))
comp.append(Part.LineSegment(App.Vector(3.737349, 5.880750, 0.000000), App.Vector(3.737349, 3.561500, 0.000000)))
comp.append(Part.LineSegment(App.Vector(3.737349, 3.561500, 0.000000), App.Vector(0.300000, 3.561500, 0.000000)))
comp.append(Part.LineSegment(App.Vector(0.300000, 3.561500, 0.000000), App.Vector(0.069250, 3.561500, 0.000000)))
comp.append(Part.LineSegment(App.Vector(0.069250, 3.561500, 0.000000), App.Vector(0.069250, 0.000000, 0.000000)))
comp.append(Part.LineSegment(App.Vector(3.298849, 2.111500, 0.000000), App.Vector(1.068099, 2.111500, 0.000000)))
comp.append(Part.LineSegment(App.Vector(1.068099, 2.111500, 0.000000), App.Vector(0.069250, 2.111500, 0.000000)))
comp.append(Part.LineSegment(App.Vector(0.069250, 0.000000, 0.000000), App.Vector(2.180750, -0.000000, 0.000000)))
comp.append(Part.LineSegment(App.Vector(2.180750, -0.000000, 0.000000), App.Vector(2.180750, 3.361500, 0.000000)))
comp.append(Part.LineSegment(App.Vector(2.180750, 3.361500, 0.000000), App.Vector(0.069250, 3.361500, 0.000000)))
comp.append(Part.LineSegment(App.Vector(0.069250, 3.361500, 0.000000), App.Vector(0.069250, 2.230750, 0.000000)))
comp.append(Part.LineSegment(App.Vector(0.069250, 2.230750, 0.000000), App.Vector(0.069250, 0.000000, 0.000000)))
comp.append(Part.LineSegment(App.Vector(0.069250, 0.000000, 0.000000), App.Vector(2.130750, -0.000000, 0.000000)))
comp.append(Part.LineSegment(App.Vector(2.130750, -0.000000, 0.000000), App.Vector(2.130750, 2.529599, 0.000000)))
comp.append(Part.LineSegment(App.Vector(2.130750, 2.529599, 0.000000), App.Vector(0.069250, 2.529599, 0.000000)))
comp.append(Part.LineSegment(App.Vector(0.069250, 2.529599, 0.000000), App.Vector(0.069250, 1.398849, 0.000000)))
comp.append(Part.LineSegment(App.Vector(0.069250, 1.398849, 0.000000), App.Vector(0.069250, 0.998849, 0.000000)))
comp.append(Part.LineSegment(App.Vector(0.069250, 0.998849, 0.000000), App.Vector(0.069250, 0.000000, 0.000000)))
comp.append(Part.LineSegment(App.Vector(0.069250, 0.000000, 0.000000), App.Vector(3.530750, 0.000000, 0.000000)))
comp.append(Part.LineSegment(App.Vector(3.530750, 0.000000, 0.000000), App.Vector(3.530750, 3.561500, 0.000000)))
comp.append(Part.LineSegment(App.Vector(3.530750, 3.561500, 0.000000), App.Vector(3.500000, 3.561500, 0.000000)))
comp.append(Part.LineSegment(App.Vector(3.500000, 3.561500, 0.000000), App.Vector(0.069250, 3.561500, 0.000000)))
comp.append(Part.LineSegment(App.Vector(5.130750, 0.000000, 0.000000), App.Vector(5.130750, 3.630750, 0.000000)))
comp.append(Part.LineSegment(App.Vector(5.130750, 3.630750, 0.000000), App.Vector(5.130750, 5.880750, 0.000000)))
comp.append(Part.LineSegment(App.Vector(5.130750, 5.880750, 0.000000), App.Vector(5.130750, 8.011500, 0.000000)))
comp.append(Part.LineSegment(App.Vector(5.130750, 8.011500, 0.000000), App.Vector(4.359369, 8.011500, 0.000000)))
comp.append(Part.LineSegment(App.Vector(4.359369, 8.011500, 0.000000), App.Vector(4.359369, 7.927740, 0.000000)))
comp.append(Part.LineSegment(App.Vector(4.172231, 7.927740, 0.000000), App.Vector(4.172231, 8.011500, 0.000000)))
comp.append(Part.LineSegment(App.Vector(4.172231, 8.011500, 0.000000), App.Vector(0.069250, 8.011500, 0.000000)))
comp.append(Part.LineSegment(App.Vector(0.069250, 8.011500, 0.000000), App.Vector(0.069250, 5.880750, 0.000000)))
comp.append(Part.LineSegment(App.Vector(0.069250, 5.880750, 0.000000), App.Vector(0.069250, 0.000000, 0.000000)))
comp.append(Part.LineSegment(App.Vector(0.100000, 0.000000, 0.000000), App.Vector(4.487049, 0.000000, 0.000000)))
comp.append(Part.LineSegment(App.Vector(4.487049, 0.000000, 0.000000), App.Vector(4.487049, 5.811500, 0.000000)))
comp.append(Part.LineSegment(App.Vector(4.487049, 5.811500, 0.000000), App.Vector(3.256299, 5.811500, 0.000000)))
comp.append(Part.LineSegment(App.Vector(3.256299, 5.811500, 0.000000), App.Vector(0.600000, 5.811500, 0.000000)))
comp.append(Part.LineSegment(App.Vector(0.600000, 5.811500, 0.000000), App.Vector(0.100000, 5.811500, 0.000000)))
comp.append(Part.LineSegment(App.Vector(0.100000, 5.811500, 0.000000), App.Vector(0.100000, 0.000000, 0.000000)))
comp.append(Part.LineSegment(App.Vector(0.000000, 0.000000, 0.000000), App.Vector(5.980750, 0.000000, 0.000000)))
comp.append(Part.LineSegment(App.Vector(5.980750, 0.000000, 0.000000), App.Vector(7.265750, -0.000000, 0.000000)))
comp.append(Part.LineSegment(App.Vector(2.568202, 3.491500, 0.000000), App.Vector(2.568202, 6.217049, 0.000000)))
comp.append(Part.LineSegment(App.Vector(2.568202, 6.217049, 0.000000), App.Vector(4.921202, 6.217049, 0.000000)))
comp.append(Part.LineSegment(App.Vector(4.921202, 6.217049, 0.000000), App.Vector(4.921202, 7.447799, 0.000000)))
comp.append(Part.LineSegment(App.Vector(4.921202, 7.447799, 0.000000), App.Vector(4.921202, 10.078549, 0.000000)))
comp.append(Part.LineSegment(App.Vector(4.921202, 10.078549, 0.000000), App.Vector(2.721202, 10.078549, 0.000000)))
comp.append(Part.LineSegment(App.Vector(2.721202, 10.078549, 0.000000), App.Vector(2.721202, 14.320030, 0.000000)))
comp.append(Part.LineSegment(App.Vector(2.721202, 14.320030, 0.000000), App.Vector(2.721202, 14.507169, 0.000000)))
comp.append(Part.LineSegment(App.Vector(2.721202, 14.507169, 0.000000), App.Vector(2.721202, 15.417049, 0.000000)))
comp.append(Part.LineSegment(App.Vector(2.721202, 15.417049, 0.000000), App.Vector(4.921202, 15.417049, 0.000000)))
comp.append(Part.LineSegment(App.Vector(4.921202, 15.417049, 0.000000), App.Vector(4.921202, 17.578549, 0.000000)))
comp.append(Part.LineSegment(App.Vector(4.921202, 17.578549, 0.000000), App.Vector(2.721202, 17.578549, 0.000000)))
comp.append(Part.LineSegment(App.Vector(2.721202, 17.578549, 0.000000), App.Vector(2.721202, 20.385149, 0.000000)))
comp.append(Part.LineSegment(App.Vector(2.721202, 20.385149, 0.000000), App.Vector(4.921202, 20.385149, 0.000000)))
comp.append(Part.LineSegment(App.Vector(4.921202, 20.385149, 0.000000), App.Vector(4.921202, 22.546649, 0.000000)))
comp.append(Part.LineSegment(App.Vector(4.921202, 22.546649, 0.000000), App.Vector(2.721202, 22.546649, 0.000000)))
comp.append(Part.LineSegment(App.Vector(2.721202, 22.546649, 0.000000), App.Vector(2.721202, 25.415899, 0.000000)))
comp.append(Part.LineSegment(App.Vector(2.721202, 25.415899, 0.000000), App.Vector(2.790452, 25.415899, 0.000000)))
comp.append(Part.LineSegment(App.Vector(2.790452, 25.415899, 0.000000), App.Vector(2.790452, 26.535247, 0.000000)))
comp.append(Part.LineSegment(App.Vector(2.790452, 26.535247, 0.000000), App.Vector(2.790452, 26.675952, 0.000000)))
comp.append(Part.LineSegment(App.Vector(2.790452, 26.675952, 0.000000), App.Vector(2.790452, 28.876949, 0.000000)))
comp.append(Part.LineSegment(App.Vector(2.790452, 28.876949, 0.000000), App.Vector(-1.944300, 28.876949, 0.000000)))
comp.append(Part.LineSegment(App.Vector(-1.944300, 28.876949, 0.000000), App.Vector(-1.944300, 20.912799, 0.000000)))
comp.append(Part.LineSegment(App.Vector(-1.944300, 20.912799, 0.000000), App.Vector(-1.831800, 20.912799, 0.000000)))
comp.append(Part.LineSegment(App.Vector(-1.831800, 20.912799, 0.000000), App.Vector(-1.831800, 20.115899, 0.000000)))
comp.append(Part.LineSegment(App.Vector(-1.831800, 20.115899, 0.000000), App.Vector(0.000000, 20.115899, 0.000000)))
comp.append(Part.LineSegment(App.Vector(0.000000, 20.115899, 0.000000), App.Vector(0.000000, 0.000000, 0.000000)))
comp.append(Part.LineSegment(App.Vector(-0.083760, 0.000000, 0.000000), App.Vector(9.660518, 0.000000, 0.000000)))
comp.append(Part.LineSegment(App.Vector(9.660518, 0.000000, 0.000000), App.Vector(9.660518, 7.365750, 0.000000)))
comp.append(Part.LineSegment(App.Vector(9.660518, 7.365750, 0.000000), App.Vector(9.660518, 8.211500, 0.000000)))
comp.append(Part.LineSegment(App.Vector(9.660518, 8.211500, 0.000000), App.Vector(-0.083760, 8.211500, 0.000000)))
comp.append(Part.LineSegment(App.Vector(-0.083760, 0.000000, 0.000000), App.Vector(7.777740, 0.000000, 0.000000)))
comp.append(Part.LineSegment(App.Vector(7.777740, 0.000000, 0.000000), App.Vector(7.777740, 8.211500, 0.000000)))
comp.append(Part.LineSegment(App.Vector(7.777740, 8.211500, 0.000000), App.Vector(-0.083760, 8.211500, 0.000000)))
comp.append(Part.LineSegment(App.Vector(-0.083760, 0.000000, 0.000000), App.Vector(5.777740, 0.000000, 0.000000)))
comp.append(Part.LineSegment(App.Vector(5.777740, 0.000000, 0.000000), App.Vector(5.777740, 8.211500, 0.000000)))
comp.append(Part.LineSegment(App.Vector(5.777740, 8.211500, 0.000000), App.Vector(-0.083760, 8.211500, 0.000000)))
comp.append(Part.LineSegment(App.Vector(0.000000, 0.000000, 0.000000), App.Vector(0.106066, 0.000000, 0.000000)))
comp.append(Part.LineSegment(App.Vector(0.106066, 0.000000, 0.000000), App.Vector(4.022731, 3.916665, 0.000000)))
comp.append(Part.LineSegment(App.Vector(4.022731, 3.916665, 0.000000), App.Vector(3.459237, 4.480158, 0.000000)))
comp.append(Part.LineSegment(App.Vector(3.459237, 4.480158, 0.000000), App.Vector(3.618336, 4.639258, 0.000000)))
comp.append(Part.LineSegment(App.Vector(3.618336, 4.639258, 0.000000), App.Vector(4.181830, 4.075764, 0.000000)))
comp.append(Part.LineSegment(App.Vector(4.181830, 4.075764, 0.000000), App.Vector(8.261412, 8.155346, 0.000000)))
comp.append(Part.LineSegment(App.Vector(8.261412, 8.155346, 0.000000), App.Vector(7.697918, 8.718840, 0.000000)))
comp.append(Part.LineSegment(App.Vector(7.697918, 8.718840, 0.000000), App.Vector(7.857017, 8.877939, 0.000000)))
comp.append(Part.LineSegment(App.Vector(7.857017, 8.877939, 0.000000), App.Vector(8.420511, 8.314445, 0.000000)))
comp.append(Part.LineSegment(App.Vector(8.420511, 8.314445, 0.000000), App.Vector(15.756744, 15.650678, 0.000000)))
comp.append(Part.LineSegment(App.Vector(15.756744, 15.650678, 0.000000), App.Vector(15.193250, 16.214172, 0.000000)))
comp.append(Part.LineSegment(App.Vector(15.193250, 16.214172, 0.000000), App.Vector(15.352349, 16.373271, 0.000000)))
comp.append(Part.LineSegment(App.Vector(15.352349, 16.373271, 0.000000), App.Vector(15.915843, 15.809777, 0.000000)))
comp.append(Part.LineSegment(App.Vector(15.915843, 15.809777, 0.000000), App.Vector(21.246014, 21.139948, 0.000000)))
comp.append(Part.LineSegment(App.Vector(21.246014, 21.139948, 0.000000), App.Vector(20.682520, 21.703441, 0.000000)))
comp.append(Part.LineSegment(App.Vector(20.682520, 21.703441, 0.000000), App.Vector(20.841619, 21.862541, 0.000000)))
comp.append(Part.LineSegment(App.Vector(20.841619, 21.862541, 0.000000), App.Vector(21.405113, 21.299047, 0.000000)))
comp.append(Part.LineSegment(App.Vector(21.405113, 21.299047, 0.000000), App.Vector(22.700391, 22.594325, 0.000000)))
comp.append(Part.LineSegment(App.Vector(22.700391, 22.594325, 0.000000), App.Vector(22.700391, 22.700391, 0.000000)))
comp.append(Part.LineSegment(App.Vector(22.700391, 22.700391, 0.000000), App.Vector(22.744776, 22.744776, 0.000000)))
comp.append(Part.LineSegment(App.Vector(22.744776, 22.744776, 0.000000), App.Vector(24.463351, 24.463351, 0.000000)))
comp.append(Part.LineSegment(App.Vector(24.463351, 24.463351, 0.000000), App.Vector(24.374962, 24.551739, 0.000000)))
comp.append(Part.LineSegment(App.Vector(24.374962, 24.551739, 0.000000), App.Vector(20.558777, 28.367924, 0.000000)))
comp.append(Part.LineSegment(App.Vector(20.558777, 28.367924, 0.000000), App.Vector(18.370353, 30.556349, 0.000000)))
comp.append(Part.LineSegment(App.Vector(18.370353, 30.556349, 0.000000), App.Vector(15.099983, 27.285979, 0.000000)))
comp.append(Part.LineSegment(App.Vector(15.099983, 27.285979, 0.000000), App.Vector(10.410945, 22.596941, 0.000000)))
comp.append(Part.LineSegment(App.Vector(10.410945, 22.596941, 0.000000), App.Vector(6.451147, 18.637143, 0.000000)))
comp.append(Part.LineSegment(App.Vector(6.451147, 18.637143, 0.000000), App.Vector(4.329827, 16.515823, 0.000000)))
comp.append(Part.LineSegment(App.Vector(4.329827, 16.515823, 0.000000), App.Vector(0.038219, 12.224215, 0.000000)))
comp.append(Part.LineSegment(App.Vector(0.038219, 12.224215, 0.000000), App.Vector(-7.032849, 5.153147, 0.000000)))
comp.append(Part.LineSegment(App.Vector(-7.032849, 5.153147, 0.000000), App.Vector(-7.875473, 4.310523, 0.000000)))
comp.append(Part.LineSegment(App.Vector(-7.875473, 4.310523, 0.000000), App.Vector(-7.831986, 4.267036, 0.000000)))
comp.append(Part.LineSegment(App.Vector(-7.831986, 4.267036, 0.000000), App.Vector(-8.527955, 3.571067, 0.000000)))
comp.append(Part.LineSegment(App.Vector(-8.527955, 3.571067, 0.000000), App.Vector(-6.661194, 1.704305, 0.000000)))
comp.append(Part.LineSegment(App.Vector(-6.661194, 1.704305, 0.000000), App.Vector(-5.965224, 2.400274, 0.000000)))
comp.append(Part.LineSegment(App.Vector(-5.965224, 2.400274, 0.000000), App.Vector(-4.126746, 0.561797, 0.000000)))
comp.append(Part.LineSegment(App.Vector(-4.126746, 0.561797, 0.000000), App.Vector(-1.782475, -1.782475, 0.000000)))
comp.append(Part.LineSegment(App.Vector(-1.782475, -1.782475, 0.000000), App.Vector(-0.044385, -0.044385, 0.000000)))
comp.append(Part.LineSegment(App.Vector(-0.044385, -0.044385, 0.000000), App.Vector(0.000000, 0.000000, 0.000000)))
comp.append(Part.LineSegment(App.Vector(0.069250, 0.000000, 0.000000), App.Vector(5.530750, 0.000000, 0.000000)))
comp.append(Part.LineSegment(App.Vector(5.530750, 0.000000, 0.000000), App.Vector(5.530750, 2.480750, 0.000000)))
comp.append(Part.LineSegment(App.Vector(5.530750, 2.480750, 0.000000), App.Vector(5.530750, 8.111500, 0.000000)))
comp.append(Part.LineSegment(App.Vector(5.530750, 8.111500, 0.000000), App.Vector(0.069250, 8.111500, 0.000000)))
comp.append(Part.LineSegment(App.Vector(0.069250, 0.000000, 0.000000), App.Vector(6.562051, 0.000000, 0.000000)))
comp.append(Part.LineSegment(App.Vector(6.562051, 0.000000, 0.000000), App.Vector(6.562051, 8.111500, 0.000000)))
comp.append(Part.LineSegment(App.Vector(6.562051, 8.111500, 0.000000), App.Vector(0.069250, 8.111500, 0.000000)))
comp.append(Part.LineSegment(App.Vector(8.257250, 0.100000, 0.000000), App.Vector(12.958752, 0.100000, 0.000000)))
comp.append(Part.LineSegment(App.Vector(12.958752, 0.100000, 0.000000), App.Vector(12.958752, 8.211500, 0.000000)))
comp.append(Part.LineSegment(App.Vector(12.958752, 8.211500, 0.000000), App.Vector(8.264500, 8.211500, 0.000000)))
comp.append(Part.LineSegment(App.Vector(8.264500, 8.211500, 0.000000), App.Vector(8.264500, 11.375650, 0.000000)))
comp.append(Part.LineSegment(App.Vector(8.264500, 11.375650, 0.000000), App.Vector(0.000000, 11.375650, 0.000000)))
comp.append(Part.LineSegment(App.Vector(0.000000, 11.375650, 0.000000), App.Vector(0.000000, 0.000000, 0.000000)))
comp.append(Part.LineSegment(App.Vector(0.069250, 0.000000, 0.000000), App.Vector(3.065000, 0.000000, 0.000000)))
comp.append(Part.LineSegment(App.Vector(3.065000, 0.000000, 0.000000), App.Vector(3.065000, -0.100000, 0.000000)))
comp.append(Part.LineSegment(App.Vector(3.065000, -0.100000, 0.000000), App.Vector(7.995750, -0.100000, 0.000000)))
comp.append(Part.LineSegment(App.Vector(7.995750, -0.100000, 0.000000), App.Vector(7.995750, 8.164500, 0.000000)))
comp.append(Part.LineSegment(App.Vector(7.995750, 8.164500, 0.000000), App.Vector(2.737349, 8.164500, 0.000000)))
comp.append(Part.LineSegment(App.Vector(2.737349, 8.164500, 0.000000), App.Vector(2.737349, 5.811500, 0.000000)))
comp.append(Part.LineSegment(App.Vector(2.737349, 5.811500, 0.000000), App.Vector(0.069250, 5.811500, 0.000000)))
comp.append(Part.LineSegment(App.Vector(0.000000, 0.000000, 0.000000), App.Vector(2.473849, -0.000000, 0.000000)))
comp.append(Part.LineSegment(App.Vector(2.473849, -0.000000, 0.000000), App.Vector(2.473849, 2.214500, 0.000000)))
comp.append(Part.LineSegment(App.Vector(2.473849, 2.214500, 0.000000), App.Vector(-0.055750, 2.214500, 0.000000)))
comp.append(Part.LineSegment(App.Vector(-0.055750, 2.214500, 0.000000), App.Vector(-0.055750, -0.000000, 0.000000)))
comp.append(Part.LineSegment(App.Vector(-0.055750, -0.000000, 0.000000), App.Vector(0.000000, 0.000000, 0.000000)))
comp.append(Part.LineSegment(App.Vector(0.069250, 0.000000, 0.000000), App.Vector(6.230750, 0.000000, 0.000000)))
comp.append(Part.LineSegment(App.Vector(6.230750, 0.000000, 0.000000), App.Vector(6.230750, 5.880750, 0.000000)))
comp.append(Part.LineSegment(App.Vector(6.230750, 5.880750, 0.000000), App.Vector(6.230750, 8.164500, 0.000000)))
comp.append(Part.LineSegment(App.Vector(6.230750, 8.164500, 0.000000), App.Vector(0.069250, 8.164500, 0.000000)))
comp.append(Part.LineSegment(App.Vector(0.069250, 8.164500, 0.000000), App.Vector(0.069250, 0.000000, 0.000000)))
comp.append(Part.LineSegment(App.Vector(0.100000, 0.000000, 0.000000), App.Vector(8.387049, 0.000000, 0.000000)))
comp.append(Part.LineSegment(App.Vector(8.387049, 0.000000, 0.000000), App.Vector(8.387049, 8.164500, 0.000000)))
comp.append(Part.LineSegment(App.Vector(8.387049, 8.164500, 0.000000), App.Vector(3.325549, 8.164500, 0.000000)))
comp.append(Part.LineSegment(App.Vector(3.325549, 8.164500, 0.000000), App.Vector(3.325549, 5.811500, 0.000000)))
comp.append(Part.LineSegment(App.Vector(3.325549, 5.811500, 0.000000), App.Vector(0.600000, 5.811500, 0.000000)))
comp.append(Part.LineSegment(App.Vector(2.568202, 6.147799, 0.000000), App.Vector(2.568202, 11.347799, 0.000000)))
comp.append(Part.LineSegment(App.Vector(2.568202, 11.347799, 0.000000), App.Vector(2.568202, 17.647799, 0.000000)))
comp.append(Part.LineSegment(App.Vector(2.568202, 17.647799, 0.000000), App.Vector(2.568202, 20.190899, 0.000000)))
comp.append(Part.LineSegment(App.Vector(2.568202, 20.190899, 0.000000), App.Vector(0.000000, 20.190899, 0.000000)))
comp.append(Part.LineSegment(App.Vector(0.000000, 20.190899, 0.000000), App.Vector(0.000000, 0.000000, 0.000000)))
comp.append(Part.LineSegment(App.Vector(0.025000, 0.000000, 0.000000), App.Vector(1.265817, 0.000000, 0.000000)))
comp.append(Part.LineSegment(App.Vector(1.265817, 0.000000, 0.000000), App.Vector(1.265817, 2.109000, 0.000000)))
comp.append(Part.LineSegment(App.Vector(1.265817, 2.109000, 0.000000), App.Vector(1.265817, 2.325000, 0.000000)))
comp.append(Part.LineSegment(App.Vector(1.265817, 2.325000, 0.000000), App.Vector(0.025000, 2.325000, 0.000000)))
comp.append(Part.LineSegment(App.Vector(0.025000, 0.000000, 0.000000), App.Vector(1.290817, 0.000000, 0.000000)))
comp.append(Part.LineSegment(App.Vector(1.290817, 0.000000, 0.000000), App.Vector(1.290817, 2.109000, 0.000000)))
comp.append(Part.LineSegment(App.Vector(1.290817, 2.109000, 0.000000), App.Vector(1.290817, 2.325000, 0.000000)))
comp.append(Part.LineSegment(App.Vector(1.290817, 2.325000, 0.000000), App.Vector(0.025000, 2.325000, 0.000000)))
comp.append(Part.LineSegment(App.Vector(0.050000, 0.000000, 0.000000), App.Vector(0.350817, 0.000000, 0.000000)))
comp.append(Part.LineSegment(App.Vector(0.350817, 0.000000, 0.000000), App.Vector(1.290817, 0.000000, 0.000000)))
comp.append(Part.LineSegment(App.Vector(1.290817, 0.000000, 0.000000), App.Vector(1.290817, 0.191000, 0.000000)))
comp.append(Part.LineSegment(App.Vector(1.290817, 0.191000, 0.000000), App.Vector(0.350817, 0.191000, 0.000000)))
comp.append(Part.LineSegment(App.Vector(0.350817, 0.191000, 0.000000), App.Vector(0.050000, 0.191000, 0.000000)))
comp.append(Part.LineSegment(App.Vector(0.050000, 0.191000, 0.000000), App.Vector(0.050000, 0.000000, 0.000000)))
comp.append(Part.LineSegment(App.Vector(0.050000, 0.000000, 0.000000), App.Vector(0.325817, 0.000000, 0.000000)))
comp.append(Part.LineSegment(App.Vector(0.325817, 0.000000, 0.000000), App.Vector(0.325817, 2.084000, 0.000000)))
comp.append(Part.LineSegment(App.Vector(0.325817, 2.084000, 0.000000), App.Vector(0.050000, 2.084000, 0.000000)))
comp.append(Part.LineSegment(App.Vector(0.050000, 2.084000, 0.000000), App.Vector(0.050000, 0.000000, 0.000000)))
comp.append(Part.LineSegment(App.Vector(0.150000, 0.000000, 0.000000), App.Vector(0.201375, 0.000000, 0.000000)))
comp.append(Part.LineSegment(App.Vector(0.201375, 0.000000, 0.000000), App.Vector(1.141375, 0.000000, 0.000000)))
comp.append(Part.LineSegment(App.Vector(1.141375, 0.000000, 0.000000), App.Vector(1.141375, 0.191000, 0.000000)))
comp.append(Part.LineSegment(App.Vector(1.141375, 0.191000, 0.000000), App.Vector(0.201375, 0.191000, 0.000000)))
comp.append(Part.LineSegment(App.Vector(0.201375, 0.191000, 0.000000), App.Vector(0.150000, 0.191000, 0.000000)))
comp.append(Part.LineSegment(App.Vector(0.150000, 0.191000, 0.000000), App.Vector(0.150000, 0.000000, 0.000000)))
comp.append(Part.LineSegment(App.Vector(-0.000000, -7.991197, 0.000000), App.Vector(8.930750, -7.991197, 0.000000)))
comp.append(Part.LineSegment(App.Vector(8.930750, -7.991197, 0.000000), App.Vector(8.930750, 0.220303, 0.000000)))
comp.append(Part.LineSegment(App.Vector(8.930750, 0.220303, 0.000000), App.Vector(0.000000, 0.220303, 0.000000)))
comp.append(Part.LineSegment(App.Vector(0.025000, 0.000000, 0.000000), App.Vector(0.305000, 0.000000, 0.000000)))
comp.append(Part.LineSegment(App.Vector(0.305000, 0.000000, 0.000000), App.Vector(0.305000, 2.084000, 0.000000)))
comp.append(Part.LineSegment(App.Vector(0.305000, 2.084000, 0.000000), App.Vector(0.025000, 2.084000, 0.000000)))
comp.append(Part.LineSegment(App.Vector(0.025000, 2.084000, 0.000000), App.Vector(0.025000, 0.000000, 0.000000)))
comp.append(Part.LineSegment(App.Vector(0.050000, 0.000000, 0.000000), App.Vector(0.965000, 0.000000, 0.000000)))
comp.append(Part.LineSegment(App.Vector(0.965000, 0.000000, 0.000000), App.Vector(0.965000, 0.191000, 0.000000)))
comp.append(Part.LineSegment(App.Vector(0.965000, 0.191000, 0.000000), App.Vector(0.050000, 0.191000, 0.000000)))
comp.append(Part.LineSegment(App.Vector(0.305000, 0.000000, 0.000000), App.Vector(0.305000, 0.191000, 0.000000)))
comp.append(Part.LineSegment(App.Vector(0.305000, 0.191000, 0.000000), App.Vector(0.025000, 0.191000, 0.000000)))
comp.append(Part.LineSegment(App.Vector(0.025000, 0.000000, 0.000000), App.Vector(1.270000, 0.000000, 0.000000)))
comp.append(Part.LineSegment(App.Vector(1.270000, 0.000000, 0.000000), App.Vector(1.270000, 2.084000, 0.000000)))
comp.append(Part.LineSegment(App.Vector(1.270000, 2.084000, 0.000000), App.Vector(0.025000, 2.084000, 0.000000)))
comp.append(Part.LineSegment(App.Vector(1.270000, 0.000000, 0.000000), App.Vector(1.270000, 0.191000, 0.000000)))
comp.append(Part.LineSegment(App.Vector(1.270000, 0.191000, 0.000000), App.Vector(0.025000, 0.191000, 0.000000)))
comp.append(Part.LineSegment(App.Vector(0.066697, 0.000000, 0.000000), App.Vector(2.031273, -0.000000, 0.000000)))
comp.append(Part.LineSegment(App.Vector(2.031273, -0.000000, 0.000000), App.Vector(1.899671, 0.491144, 0.000000)))
comp.append(Part.LineSegment(App.Vector(1.899671, 0.491144, 0.000000), App.Vector(0.066697, 0.000000, 0.000000)))
comp.append(Part.LineSegment(App.Vector(0.012484, 0.000000, 0.000000), App.Vector(0.902512, -0.000000, 0.000000)))
comp.append(Part.LineSegment(App.Vector(0.902512, -0.000000, 0.000000), App.Vector(1.880048, 0.564381, 0.000000)))
comp.append(Part.LineSegment(App.Vector(1.880048, 0.564381, 0.000000), App.Vector(1.760971, 1.008782, 0.000000)))
comp.append(Part.LineSegment(App.Vector(1.760971, 1.008782, 0.000000), App.Vector(-0.122585, 0.504085, 0.000000)))
comp.append(Part.LineSegment(App.Vector(-0.122585, 0.504085, 0.000000), App.Vector(0.012484, 0.000000, 0.000000)))
comp.append(Part.LineSegment(App.Vector(0.039279, -0.000000, 0.000000), App.Vector(1.765121, 0.000000, 0.000000)))
comp.append(Part.LineSegment(App.Vector(1.765121, 0.000000, 0.000000), App.Vector(0.154889, 0.431460, 0.000000)))
comp.append(Part.LineSegment(App.Vector(0.154889, 0.431460, 0.000000), App.Vector(0.039279, 0.000000, 0.000000)))
comp.append(Part.LineSegment(App.Vector(2.415000, 0.000000, 0.000000), App.Vector(2.415000, 0.176838, 0.000000)))
comp.append(Part.LineSegment(App.Vector(2.415000, 0.176838, 0.000000), App.Vector(1.071961, 0.536704, 0.000000)))
comp.append(Part.LineSegment(App.Vector(1.071961, 0.536704, 0.000000), App.Vector(1.084902, 0.560000, 0.000000)))
comp.append(Part.LineSegment(App.Vector(1.084902, 0.560000, 0.000000), App.Vector(0.025000, 0.560000, 0.000000)))
comp.append(Part.LineSegment(App.Vector(2.415000, 0.560000, 0.000000), App.Vector(1.355098, 0.560000, 0.000000)))
comp.append(Part.LineSegment(App.Vector(1.355098, 0.560000, 0.000000), App.Vector(1.368039, 0.536704, 0.000000)))
comp.append(Part.LineSegment(App.Vector(1.368039, 0.536704, 0.000000), App.Vector(0.025000, 0.176838, 0.000000)))
comp.append(Part.LineSegment(App.Vector(0.025000, 0.176838, 0.000000), App.Vector(0.025000, 0.000000, 0.000000)))
comp.append(Part.LineSegment(App.Vector(0.150000, 0.000000, 0.000000), App.Vector(0.532200, 0.000000, 0.000000)))
comp.append(Part.LineSegment(App.Vector(0.532200, 0.000000, 0.000000), App.Vector(0.532200, 0.220634, 0.000000)))
comp.append(Part.LineSegment(App.Vector(0.532200, 0.220634, 0.000000), App.Vector(0.150000, 0.323044, 0.000000)))
comp.append(Part.LineSegment(App.Vector(0.150000, 0.323044, 0.000000), App.Vector(0.150000, -0.000000, 0.000000)))
comp.append(Part.LineSegment(App.Vector(0.025000, 0.000000, 0.000000), App.Vector(0.798416, 0.000000, 0.000000)))
comp.append(Part.LineSegment(App.Vector(0.798416, -0.000000, 0.000000), App.Vector(0.025000, 0.207236, 0.000000)))
comp.append(Part.LineSegment(App.Vector(0.025000, 0.207236, 0.000000), App.Vector(0.025000, 0.000000, 0.000000)))
comp.append(Part.LineSegment(App.Vector(0.286486, 0.000000, 0.000000), App.Vector(1.059902, 0.000000, 0.000000)))
comp.append(Part.LineSegment(App.Vector(1.059902, 0.000000, 0.000000), App.Vector(1.059902, 0.207236, 0.000000)))
comp.append(Part.LineSegment(App.Vector(1.059902, 0.207236, 0.000000), App.Vector(0.286486, 0.000000, 0.000000)))
comp.append(Part.LineSegment(App.Vector(-1.529901, 0.000000, 0.000000), App.Vector(0.000000, 0.000000, 0.000000)))
comp.append(Part.LineSegment(App.Vector(0.000000, -0.000000, 0.000000), App.Vector(-1.529901, 1.583870, 0.000000)))
comp.append(Part.LineSegment(App.Vector(-1.529901, 1.583870, 0.000000), App.Vector(-1.529901, 0.000000, 0.000000)))
comp.append(Part.LineSegment(App.Vector(0.000000, 0.000000, 0.000000), App.Vector(0.000000, 1.583870, 0.000000)))
comp.append(Part.LineSegment(App.Vector(0.000000, 1.583870, 0.000000), App.Vector(-0.003199, 1.587182, 0.000000)))
comp.append(Part.LineSegment(App.Vector(-0.003199, 1.587182, 0.000000), App.Vector(-1.270225, 1.587182, 0.000000)))
comp.append(Part.LineSegment(App.Vector(-1.270225, 1.587182, 0.000000), App.Vector(-1.270225, 0.000000, 0.000000)))
comp.append(Part.LineSegment(App.Vector(-1.529000, 0.000000, 0.000000), App.Vector(0.000000, 0.000000, 0.000000)))
comp.append(Part.LineSegment(App.Vector(0.000000, 0.000000, 0.000000), App.Vector(-1.529000, 1.582937, 0.000000)))
comp.append(Part.LineSegment(App.Vector(-1.529000, 1.582937, 0.000000), App.Vector(-1.529000, 0.000000, 0.000000)))
comp.append(Part.LineSegment(App.Vector(0.000000, 0.000000, 0.000000), App.Vector(0.000000, 1.582937, 0.000000)))
comp.append(Part.LineSegment(App.Vector(0.000000, 1.582937, 0.000000), App.Vector(-0.004100, 1.587182, 0.000000)))
comp.append(Part.LineSegment(App.Vector(-0.004100, 1.587182, 0.000000), App.Vector(-1.270225, 1.587182, 0.000000)))
comp.append(Part.LineSegment(App.Vector(0.000000, 0.000000, 0.000000), App.Vector(-1.533100, 1.587182, 0.000000)))
comp.append(Part.LineSegment(App.Vector(-1.533100, 1.587182, 0.000000), App.Vector(-1.560901, 1.587182, 0.000000)))
comp.append(Part.LineSegment(App.Vector(-1.560901, 1.587182, 0.000000), App.Vector(-1.560901, 0.000000, 0.000000)))
comp.append(Part.LineSegment(App.Vector(-1.533100, 1.587182, 0.000000), App.Vector(-1.560000, 1.587182, 0.000000)))
comp.append(Part.LineSegment(App.Vector(-1.560000, 1.587182, 0.000000), App.Vector(-1.560000, 0.000000, 0.000000)))
comp.append(Part.LineSegment(App.Vector(1.336629, 0.000000, 0.000000), App.Vector(1.336629, 1.060000, 0.000000)))
comp.append(Part.LineSegment(App.Vector(1.336629, 1.060000, 0.000000), App.Vector(0.050000, 1.060000, 0.000000)))
comp.append(Part.LineSegment(App.Vector(0.050000, 1.060000, 0.000000), App.Vector(0.050000, 0.000000, 0.000000)))
comp.append(Part.LineSegment(App.Vector(1.336629, 1.060000, 0.000000), App.Vector(0.025000, 1.060000, 0.000000)))
comp.append(Part.LineSegment(App.Vector(0.025000, 1.060000, 0.000000), App.Vector(0.025000, 0.000000, 0.000000)))
comp.append(Part.LineSegment(App.Vector(0.025000, 0.000000, 0.000000), App.Vector(0.421629, 0.000000, 0.000000)))
comp.append(Part.LineSegment(App.Vector(0.421629, 0.000000, 0.000000), App.Vector(1.336629, 0.000000, 0.000000)))
comp.append(Part.LineSegment(App.Vector(1.336629, 1.060000, 0.000000), App.Vector(0.421629, 1.060000, 0.000000)))
comp.append(Part.LineSegment(App.Vector(0.421629, 1.060000, 0.000000), App.Vector(0.025000, 1.060000, 0.000000)))
comp.append(Part.LineSegment(App.Vector(0.940000, 0.000000, 0.000000), App.Vector(1.336629, 0.000000, 0.000000)))
comp.append(Part.LineSegment(App.Vector(1.336629, 1.060000, 0.000000), App.Vector(0.940000, 1.060000, 0.000000)))
comp.append(Part.LineSegment(App.Vector(0.940000, 1.060000, 0.000000), App.Vector(0.025000, 1.060000, 0.000000)))
comp.append(Part.LineSegment(App.Vector(1.290817, 0.000000, 0.000000), App.Vector(1.290817, 1.060000, 0.000000)))
comp.append(Part.LineSegment(App.Vector(1.290817, 1.060000, 0.000000), App.Vector(0.350817, 1.060000, 0.000000)))
comp.append(Part.LineSegment(App.Vector(0.350817, 1.060000, 0.000000), App.Vector(0.050000, 1.060000, 0.000000)))
comp.append(Part.LineSegment(App.Vector(1.265817, 0.000000, 0.000000), App.Vector(1.265817, 1.060000, 0.000000)))
comp.append(Part.LineSegment(App.Vector(1.265817, 1.060000, 0.000000), App.Vector(0.025000, 1.060000, 0.000000)))
comp.append(Part.LineSegment(App.Vector(1.290817, 1.060000, 0.000000), App.Vector(0.025000, 1.060000, 0.000000)))
comp.append(Part.LineSegment(App.Vector(0.050000, 0.000000, 0.000000), App.Vector(0.201375, 0.000000, 0.000000)))
comp.append(Part.LineSegment(App.Vector(1.141375, 0.000000, 0.000000), App.Vector(1.141375, 1.060000, 0.000000)))
comp.append(Part.LineSegment(App.Vector(1.141375, 1.060000, 0.000000), App.Vector(0.201375, 1.060000, 0.000000)))
comp.append(Part.LineSegment(App.Vector(0.201375, 1.060000, 0.000000), App.Vector(0.050000, 1.060000, 0.000000)))
comp.append(Part.LineSegment(App.Vector(0.025000, 0.000000, 0.000000), App.Vector(1.141375, 0.000000, 0.000000)))
comp.append(Part.LineSegment(App.Vector(1.141375, 1.060000, 0.000000), App.Vector(0.025000, 1.060000, 0.000000)))
comp.append(Part.LineSegment(App.Vector(0.025000, 0.000000, 0.000000), App.Vector(1.116375, 0.000000, 0.000000)))
comp.append(Part.LineSegment(App.Vector(1.116375, 0.000000, 0.000000), App.Vector(1.116375, 1.060000, 0.000000)))
comp.append(Part.LineSegment(App.Vector(1.116375, 1.060000, 0.000000), App.Vector(0.025000, 1.060000, 0.000000)))
comp.append(Part.LineSegment(App.Vector(0.050000, 0.000000, 0.000000), App.Vector(1.105600, 0.000000, 0.000000)))
comp.append(Part.LineSegment(App.Vector(1.105600, 0.000000, 0.000000), App.Vector(1.105600, 1.060000, 0.000000)))
comp.append(Part.LineSegment(App.Vector(1.105600, 1.060000, 0.000000), App.Vector(0.050000, 1.060000, 0.000000)))
comp.append(Part.LineSegment(App.Vector(0.025000, 0.000000, 0.000000), App.Vector(1.105600, 0.000000, 0.000000)))
comp.append(Part.LineSegment(App.Vector(1.105600, 1.060000, 0.000000), App.Vector(0.025000, 1.060000, 0.000000)))
comp.append(Part.LineSegment(App.Vector(1.975000, 0.000000, 0.000000), App.Vector(1.975000, 0.930000, 0.000000)))
comp.append(Part.LineSegment(App.Vector(1.975000, 0.930000, 0.000000), App.Vector(0.050000, 0.930000, 0.000000)))
comp.append(Part.LineSegment(App.Vector(0.050000, 0.930000, 0.000000), App.Vector(0.050000, 0.000000, 0.000000)))
comp.append(Part.LineSegment(App.Vector(1.975000, 0.930000, 0.000000), App.Vector(0.025000, 0.930000, 0.000000)))
comp.append(Part.LineSegment(App.Vector(0.025000, 0.930000, 0.000000), App.Vector(0.025000, 0.000000, 0.000000)))
comp.append(Part.LineSegment(App.Vector(1.975000, 0.930000, 0.000000), App.Vector(0.120000, 0.930000, 0.000000)))
comp.append(Part.LineSegment(App.Vector(0.120000, 0.930000, 0.000000), App.Vector(0.025000, 0.930000, 0.000000)))
comp.append(Part.LineSegment(App.Vector(1.975000, 0.930000, 0.000000), App.Vector(1.880000, 0.930000, 0.000000)))
comp.append(Part.LineSegment(App.Vector(1.880000, 0.930000, 0.000000), App.Vector(0.025000, 0.930000, 0.000000)))
comp.append(Part.LineSegment(App.Vector(1.911352, 0.000000, 0.000000), App.Vector(1.911352, 0.930000, 0.000000)))
comp.append(Part.LineSegment(App.Vector(1.911352, 0.930000, 0.000000), App.Vector(0.025000, 0.930000, 0.000000)))
comp.append(Part.LineSegment(App.Vector(0.965000, 0.000000, 0.000000), App.Vector(0.965000, 1.060000, 0.000000)))
comp.append(Part.LineSegment(App.Vector(0.965000, 1.060000, 0.000000), App.Vector(0.050000, 1.060000, 0.000000)))
comp.append(Part.LineSegment(App.Vector(0.305000, 0.000000, 0.000000), App.Vector(0.305000, 1.060000, 0.000000)))
comp.append(Part.LineSegment(App.Vector(0.305000, 1.060000, 0.000000), App.Vector(0.025000, 1.060000, 0.000000)))
comp.append(Part.LineSegment(App.Vector(1.270000, 0.000000, 0.000000), App.Vector(1.270000, 1.060000, 0.000000)))
comp.append(Part.LineSegment(App.Vector(1.270000, 1.060000, 0.000000), App.Vector(0.025000, 1.060000, 0.000000)))
comp.append(Part.LineSegment(App.Vector(0.000000, 0.000000, 0.000000), App.Vector(49.225077, 0.000000, 0.000000)))
comp.append(Part.LineSegment(App.Vector(49.225077, 0.000000, 0.000000), App.Vector(49.225077, -5.539000, 0.000000)))
comp.append(Part.LineSegment(App.Vector(49.225077, -5.539000, 0.000000), App.Vector(50.021978, -5.539000, 0.000000)))
comp.append(Part.LineSegment(App.Vector(50.021978, -5.539000, 0.000000), App.Vector(50.021978, -5.764000, 0.000000)))
comp.append(Part.LineSegment(App.Vector(50.021978, -5.764000, 0.000000), App.Vector(49.225077, -5.764000, 0.000000)))
comp.append(Part.LineSegment(App.Vector(49.225077, -5.764000, 0.000000), App.Vector(49.225077, -11.533401, 0.000000)))
comp.append(Part.LineSegment(App.Vector(49.225077, -11.533401, 0.000000), App.Vector(50.021978, -11.533401, 0.000000)))
comp.append(Part.LineSegment(App.Vector(50.021978, -11.533401, 0.000000), App.Vector(50.021978, -11.758401, 0.000000)))
comp.append(Part.LineSegment(App.Vector(50.021978, -11.758401, 0.000000), App.Vector(49.225077, -11.758401, 0.000000)))
comp.append(Part.LineSegment(App.Vector(49.225077, -11.758401, 0.000000), App.Vector(49.225077, -22.133401, 0.000000)))
comp.append(Part.LineSegment(App.Vector(49.225077, -22.133401, 0.000000), App.Vector(50.021978, -22.133401, 0.000000)))
comp.append(Part.LineSegment(App.Vector(50.021978, -22.133401, 0.000000), App.Vector(50.021978, -22.358401, 0.000000)))
comp.append(Part.LineSegment(App.Vector(50.021978, -22.358401, 0.000000), App.Vector(49.225077, -22.358401, 0.000000)))
comp.append(Part.LineSegment(App.Vector(49.225077, -22.358401, 0.000000), App.Vector(49.225077, -29.896401, 0.000000)))
comp.append(Part.LineSegment(App.Vector(49.225077, -29.896401, 0.000000), App.Vector(50.021978, -29.896401, 0.000000)))
comp.append(Part.LineSegment(App.Vector(50.021978, -29.896401, 0.000000), App.Vector(50.021978, -30.121401, 0.000000)))
comp.append(Part.LineSegment(App.Vector(50.021978, -30.121401, 0.000000), App.Vector(49.225077, -30.121401, 0.000000)))
comp.append(Part.LineSegment(App.Vector(49.225077, -30.121401, 0.000000), App.Vector(49.225077, -31.953201, 0.000000)))
comp.append(Part.LineSegment(App.Vector(49.225077, -31.953201, 0.000000), App.Vector(29.109178, -31.953201, 0.000000)))
comp.append(Part.LineSegment(App.Vector(29.109178, -31.953201, 0.000000), App.Vector(29.109178, -34.674402, 0.000000)))
comp.append(Part.LineSegment(App.Vector(29.109178, -34.674402, 0.000000), App.Vector(29.260678, -34.674402, 0.000000)))
comp.append(Part.LineSegment(App.Vector(29.260678, -34.674402, 0.000000), App.Vector(29.260678, -35.658652, 0.000000)))
comp.append(Part.LineSegment(App.Vector(29.260678, -35.658652, 0.000000), App.Vector(31.900678, -35.658652, 0.000000)))
comp.append(Part.LineSegment(App.Vector(31.900678, -35.658652, 0.000000), App.Vector(31.900678, -34.521402, 0.000000)))
comp.append(Part.LineSegment(App.Vector(31.900678, -34.521402, 0.000000), App.Vector(57.916878, -34.521402, 0.000000)))
comp.append(Part.LineSegment(App.Vector(57.916878, -34.521402, 0.000000), App.Vector(57.916878, 2.595800, 0.000000)))
comp.append(Part.LineSegment(App.Vector(57.916878, 2.595800, 0.000000), App.Vector(57.855378, 2.595800, 0.000000)))
comp.append(Part.LineSegment(App.Vector(57.855378, 2.595800, 0.000000), App.Vector(57.855378, 3.580050, 0.000000)))
comp.append(Part.LineSegment(App.Vector(57.855378, 3.580050, 0.000000), App.Vector(55.215378, 3.580050, 0.000000)))
comp.append(Part.LineSegment(App.Vector(55.215378, 3.580050, 0.000000), App.Vector(55.215378, 2.595800, 0.000000)))
comp.append(Part.LineSegment(App.Vector(55.215378, 2.595800, 0.000000), App.Vector(49.155827, 2.595800, 0.000000)))
comp.append(Part.LineSegment(App.Vector(49.155827, 2.595800, 0.000000), App.Vector(49.155827, 4.910800, 0.000000)))
comp.append(Part.LineSegment(App.Vector(49.155827, 4.910800, 0.000000), App.Vector(47.594327, 4.910800, 0.000000)))
comp.append(Part.LineSegment(App.Vector(47.594327, 4.910800, 0.000000), App.Vector(47.594327, 2.595800, 0.000000)))
comp.append(Part.LineSegment(App.Vector(47.594327, 2.595800, 0.000000), App.Vector(45.453528, 2.595800, 0.000000)))
comp.append(Part.LineSegment(App.Vector(45.453528, 2.595800, 0.000000), App.Vector(45.453528, 4.910800, 0.000000)))
comp.append(Part.LineSegment(App.Vector(45.453528, 4.910800, 0.000000), App.Vector(43.892028, 4.910800, 0.000000)))
comp.append(Part.LineSegment(App.Vector(43.892028, 4.910800, 0.000000), App.Vector(43.892028, 2.595800, 0.000000)))
comp.append(Part.LineSegment(App.Vector(43.892028, 2.595800, 0.000000), App.Vector(2.740000, 2.595800, 0.000000)))
comp.append(Part.LineSegment(App.Vector(2.740000, 2.595800, 0.000000), App.Vector(2.740000, 3.580050, 0.000000)))
comp.append(Part.LineSegment(App.Vector(2.740000, 3.580050, 0.000000), App.Vector(0.100000, 3.580050, 0.000000)))
comp.append(Part.LineSegment(App.Vector(0.100000, 3.580050, 0.000000), App.Vector(0.100000, 2.595800, 0.000000)))
comp.append(Part.LineSegment(App.Vector(0.100000, 2.595800, 0.000000), App.Vector(0.000000, 2.595800, 0.000000)))
comp.append(Part.LineSegment(App.Vector(50.021978, -29.896401, 0.000000), App.Vector(50.021978, -30.008901, 0.000000)))
comp.append(Part.LineSegment(App.Vector(50.021978, -30.008901, 0.000000), App.Vector(57.916878, -30.008901, 0.000000)))
comp.append(Part.LineSegment(App.Vector(57.916878, -30.008901, 0.000000), App.Vector(57.916878, 2.595800, 0.000000)))
comp.append(Part.LineSegment(App.Vector(-2.740000, -0.000000, 0.000000), App.Vector(-0.100000, -0.000000, 0.000000)))
comp.append(Part.LineSegment(App.Vector(-0.100000, -0.000000, 0.000000), App.Vector(-0.100000, 1.137250, 0.000000)))
comp.append(Part.LineSegment(App.Vector(-0.100000, 1.137250, 0.000000), App.Vector(3.325549, 1.137250, 0.000000)))
comp.append(Part.LineSegment(App.Vector(3.325549, 1.137250, 0.000000), App.Vector(3.325549, -1.215750, 0.000000)))
comp.append(Part.LineSegment(App.Vector(3.325549, -1.215750, 0.000000), App.Vector(7.187049, -1.215750, 0.000000)))
comp.append(Part.LineSegment(App.Vector(7.187049, -1.215750, 0.000000), App.Vector(7.187049, 0.984250, 0.000000)))
comp.append(Part.LineSegment(App.Vector(7.187049, 0.984250, 0.000000), App.Vector(12.525549, 0.984250, 0.000000)))
comp.append(Part.LineSegment(App.Vector(12.525549, 0.984250, 0.000000), App.Vector(12.525549, -1.215750, 0.000000)))
comp.append(Part.LineSegment(App.Vector(12.525549, -1.215750, 0.000000), App.Vector(14.687049, -1.215750, 0.000000)))
comp.append(Part.LineSegment(App.Vector(14.687049, -1.215750, 0.000000), App.Vector(14.687049, 0.984250, 0.000000)))
comp.append(Part.LineSegment(App.Vector(14.687049, 0.984250, 0.000000), App.Vector(17.493649, 0.984250, 0.000000)))
comp.append(Part.LineSegment(App.Vector(17.493649, 0.984250, 0.000000), App.Vector(17.493649, -1.215750, 0.000000)))
comp.append(Part.LineSegment(App.Vector(17.493649, -1.215750, 0.000000), App.Vector(19.655149, -1.215750, 0.000000)))
comp.append(Part.LineSegment(App.Vector(19.655149, -1.215750, 0.000000), App.Vector(19.655149, 0.984250, 0.000000)))
comp.append(Part.LineSegment(App.Vector(19.655149, 0.984250, 0.000000), App.Vector(22.524399, 0.984250, 0.000000)))
comp.append(Part.LineSegment(App.Vector(22.524399, 0.984250, 0.000000), App.Vector(22.524399, 0.915000, 0.000000)))
comp.append(Part.LineSegment(App.Vector(22.524399, 0.915000, 0.000000), App.Vector(25.985449, 0.915000, 0.000000)))
comp.append(Part.LineSegment(App.Vector(25.985449, 0.915000, 0.000000), App.Vector(25.985449, 5.649752, 0.000000)))
comp.append(Part.LineSegment(App.Vector(25.985449, 5.649752, 0.000000), App.Vector(18.021299, 5.649752, 0.000000)))
comp.append(Part.LineSegment(App.Vector(18.021299, 5.649752, 0.000000), App.Vector(18.021299, 5.537252, 0.000000)))
comp.append(Part.LineSegment(App.Vector(18.021299, 5.537252, 0.000000), App.Vector(17.224399, 5.537252, 0.000000)))
comp.append(Part.LineSegment(App.Vector(17.224399, 5.537252, 0.000000), App.Vector(17.224399, 3.705452, 0.000000)))
comp.append(Part.LineSegment(App.Vector(17.224399, 3.705452, 0.000000), App.Vector(-2.891500, 3.705452, 0.000000)))
comp.append(Part.LineSegment(App.Vector(-2.891500, 3.705452, 0.000000), App.Vector(-2.891500, 0.984250, 0.000000)))
comp.append(Part.LineSegment(App.Vector(-2.891500, 0.984250, 0.000000), App.Vector(-2.740000, 0.984250, 0.000000)))
comp.append(Part.LineSegment(App.Vector(-2.740000, 0.984250, 0.000000), App.Vector(-2.740000, -0.000000, 0.000000)))
comp.append(Part.LineSegment(App.Vector(0.000000, 0.000000, 0.000000), App.Vector(2.134000, 0.000000, 0.000000)))
comp.append(Part.LineSegment(App.Vector(2.134000, 0.000000, 0.000000), App.Vector(2.134000, 0.915000, 0.000000)))
comp.append(Part.LineSegment(App.Vector(2.134000, 0.915000, 0.000000), App.Vector(0.000000, 0.915000, 0.000000)))
comp.append(Part.LineSegment(App.Vector(0.000000, 0.915000, 0.000000), App.Vector(0.000000, 0.000000, 0.000000)))
comp.append(Part.LineSegment(App.Vector(0.152000, 0.152000, 0.000000), App.Vector(0.152000, 0.279000, 0.000000)))
comp.append(Part.LineSegment(App.Vector(0.152000, 0.279000, 0.000000), App.Vector(0.787000, 0.279000, 0.000000)))
comp.append(Part.LineSegment(App.Vector(0.787000, 0.279000, 0.000000), App.Vector(0.787000, 0.152000, 0.000000)))
comp.append(Part.LineSegment(App.Vector(0.787000, 0.152000, 0.000000), App.Vector(0.152000, 0.152000, 0.000000)))
comp.append(Part.LineSegment(App.Vector(0.000000, 0.000000, 0.000000), App.Vector(0.635000, 0.000000, 0.000000)))
comp.append(Part.LineSegment(App.Vector(0.635000, 0.000000, 0.000000), App.Vector(0.635000, 0.127000, 0.000000)))
comp.append(Part.LineSegment(App.Vector(0.635000, 0.127000, 0.000000), App.Vector(0.000000, 0.127000, 0.000000)))
comp.append(Part.LineSegment(App.Vector(0.000000, 0.127000, 0.000000), App.Vector(0.000000, 0.000000, 0.000000)))
comp.append(Part.LineSegment(App.Vector(-0.127000, -0.000000, 0.000000), App.Vector(0.000000, -0.000000, 0.000000)))
comp.append(Part.LineSegment(App.Vector(0.000000, -0.000000, 0.000000), App.Vector(0.000000, 0.635000, 0.000000)))
comp.append(Part.LineSegment(App.Vector(0.000000, 0.635000, 0.000000), App.Vector(-0.127000, 0.635000, 0.000000)))
comp.append(Part.LineSegment(App.Vector(-0.127000, 0.635000, 0.000000), App.Vector(-0.127000, -0.000000, 0.000000)))
comp.append(Part.LineSegment(App.Vector(2.134000, 0.000000, 0.000000), App.Vector(2.134000, 0.076000, 0.000000)))
comp.append(Part.LineSegment(App.Vector(2.134000, 0.076000, 0.000000), App.Vector(-0.076000, 0.076000, 0.000000)))
comp.append(Part.LineSegment(App.Vector(-0.076000, 0.076000, 0.000000), App.Vector(-0.076000, -0.991000, 0.000000)))
comp.append(Part.LineSegment(App.Vector(-0.076000, -0.991000, 0.000000), App.Vector(2.134000, -0.991000, 0.000000)))
comp.append(Part.LineSegment(App.Vector(2.134000, -0.991000, 0.000000), App.Vector(2.134000, -0.915000, 0.000000)))
comp.append(Part.LineSegment(App.Vector(2.134000, -0.915000, 0.000000), App.Vector(0.000000, -0.915000, 0.000000)))
comp.append(Part.LineSegment(App.Vector(0.000000, -0.915000, 0.000000), App.Vector(0.000000, 0.000000, 0.000000)))
comp.append(Part.LineSegment(App.Vector(-1.067000, -0.000000, 0.000000), App.Vector(0.000000, 0.000000, 0.000000)))
comp.append(Part.LineSegment(App.Vector(0.000000, 0.000000, 0.000000), App.Vector(0.000000, 2.210000, 0.000000)))
comp.append(Part.LineSegment(App.Vector(0.000000, 2.210000, 0.000000), App.Vector(-0.076000, 2.210000, 0.000000)))
comp.append(Part.LineSegment(App.Vector(-0.076000, 2.210000, 0.000000), App.Vector(-0.076000, 0.076000, 0.000000)))
comp.append(Part.LineSegment(App.Vector(-0.076000, 0.076000, 0.000000), App.Vector(-0.991000, 0.076000, 0.000000)))
comp.append(Part.LineSegment(App.Vector(-0.991000, 0.076000, 0.000000), App.Vector(-0.991000, 2.210000, 0.000000)))
comp.append(Part.LineSegment(App.Vector(-0.991000, 2.210000, 0.000000), App.Vector(-1.067000, 2.210000, 0.000000)))
comp.append(Part.LineSegment(App.Vector(-1.067000, 2.210000, 0.000000), App.Vector(-1.067000, -0.000000, 0.000000)))
comp.append(Part.LineSegment(App.Vector(-0.475000, 0.000000, 0.000000), App.Vector(0.000000, 0.000000, 0.000000)))
comp.append(Part.LineSegment(App.Vector(0.000000, 0.000000, 0.000000), App.Vector(0.000000, 0.475000, 0.000000)))
comp.append(Part.LineSegment(App.Vector(0.000000, 0.475000, 0.000000), App.Vector(-0.475000, 0.475000, 0.000000)))
comp.append(Part.LineSegment(App.Vector(-0.475000, 0.475000, 0.000000), App.Vector(-0.475000, 0.000000, 0.000000)))
comp.append(Part.LineSegment(App.Vector(-1.830000, -0.000000, 0.000000), App.Vector(0.000000, -0.000000, 0.000000)))
comp.append(Part.LineSegment(App.Vector(0.000000, -0.000000, 0.000000), App.Vector(0.000000, 2.134000, 0.000000)))
comp.append(Part.LineSegment(App.Vector(0.000000, 2.134000, 0.000000), App.Vector(-1.830000, 2.134000, 0.000000)))
comp.append(Part.LineSegment(App.Vector(-1.830000, 2.134000, 0.000000), App.Vector(-1.830000, -0.000000, 0.000000)))
comp.append(Part.LineSegment(App.Vector(-0.813400, 0.102000, 0.000000), App.Vector(-0.813400, 2.032000, 0.000000)))
comp.append(Part.LineSegment(App.Vector(-0.813400, 2.032000, 0.000000), App.Vector(-0.101600, 2.032000, 0.000000)))
comp.append(Part.LineSegment(App.Vector(-0.101600, 2.032000, 0.000000), App.Vector(-0.101600, 0.102000, 0.000000)))
comp.append(Part.LineSegment(App.Vector(-0.101600, 0.102000, 0.000000), App.Vector(-0.813400, 0.102000, 0.000000)))
comp.append(Part.LineSegment(App.Vector(-1.728400, 0.102000, 0.000000), App.Vector(-1.728400, 2.032000, 0.000000)))
comp.append(Part.LineSegment(App.Vector(-1.728400, 2.032000, 0.000000), App.Vector(-1.016600, 2.032000, 0.000000)))
comp.append(Part.LineSegment(App.Vector(-1.016600, 2.032000, 0.000000), App.Vector(-1.016600, 0.102000, 0.000000)))
comp.append(Part.LineSegment(App.Vector(-1.016600, 0.102000, 0.000000), App.Vector(-1.728400, 0.102000, 0.000000)))
comp.append(Part.LineSegment(App.Vector(0.000000, 0.000000, 0.000000), App.Vector(1.930000, 0.000000, 0.000000)))
comp.append(Part.LineSegment(App.Vector(1.930000, 0.000000, 0.000000), App.Vector(1.930000, 0.711800, 0.000000)))
comp.append(Part.LineSegment(App.Vector(1.930000, 0.711800, 0.000000), App.Vector(0.000000, 0.711800, 0.000000)))
comp.append(Part.LineSegment(App.Vector(0.000000, 0.711800, 0.000000), App.Vector(0.000000, 0.000000, 0.000000)))
comp.append(Part.LineSegment(App.Vector(-0.711800, -0.000000, 0.000000), App.Vector(0.000000, -0.000000, 0.000000)))
comp.append(Part.LineSegment(App.Vector(-0.000000, -0.000000, 0.000000), App.Vector(-0.000000, 1.930000, 0.000000)))
comp.append(Part.LineSegment(App.Vector(-0.000000, 1.930000, 0.000000), App.Vector(-0.711800, 1.930000, 0.000000)))
comp.append(Part.LineSegment(App.Vector(-0.711800, 1.930000, 0.000000), App.Vector(-0.711800, -0.000000, 0.000000)))
comp.append(Part.LineSegment(App.Vector(0.000000, 0.000000, 0.000000), App.Vector(1.830000, 0.000000, 0.000000)))
comp.append(Part.LineSegment(App.Vector(1.830000, 0.000000, 0.000000), App.Vector(1.830000, -2.134000, 0.000000)))
comp.append(Part.LineSegment(App.Vector(1.830000, -2.134000, 0.000000), App.Vector(1.906000, -2.134000, 0.000000)))
comp.append(Part.LineSegment(App.Vector(1.906000, -2.134000, 0.000000), App.Vector(1.906000, 0.076000, 0.000000)))
comp.append(Part.LineSegment(App.Vector(1.906000, 0.076000, 0.000000), App.Vector(-0.076000, 0.076000, 0.000000)))
comp.append(Part.LineSegment(App.Vector(-0.076000, 0.076000, 0.000000), App.Vector(-0.076000, -2.134000, 0.000000)))
comp.append(Part.LineSegment(App.Vector(-0.076000, -2.134000, 0.000000), App.Vector(0.000000, -2.134000, 0.000000)))
comp.append(Part.LineSegment(App.Vector(0.000000, -2.134000, 0.000000), App.Vector(0.000000, 0.000000, 0.000000)))
comp.append(Part.LineSegment(App.Vector(0.000000, 0.000000, 0.000000), App.Vector(2.210000, 0.000000, 0.000000)))
comp.append(Part.LineSegment(App.Vector(2.210000, 0.000000, 0.000000), App.Vector(2.210000, 1.982000, 0.000000)))
comp.append(Part.LineSegment(App.Vector(2.210000, 1.982000, 0.000000), App.Vector(0.000000, 1.982000, 0.000000)))
comp.append(Part.LineSegment(App.Vector(0.000000, 1.982000, 0.000000), App.Vector(0.000000, 1.906000, 0.000000)))
comp.append(Part.LineSegment(App.Vector(0.000000, 1.906000, 0.000000), App.Vector(2.134000, 1.906000, 0.000000)))
comp.append(Part.LineSegment(App.Vector(2.134000, 1.906000, 0.000000), App.Vector(2.134000, 0.076000, 0.000000)))
comp.append(Part.LineSegment(App.Vector(2.134000, 0.076000, 0.000000), App.Vector(0.000000, 0.076000, 0.000000)))
comp.append(Part.LineSegment(App.Vector(0.000000, 0.076000, 0.000000), App.Vector(0.000000, 0.000000, 0.000000)))
comp.append(Part.LineSegment(App.Vector(-1.828800, -0.000000, 0.000000), App.Vector(0.000000, 0.000000, 0.000000)))
comp.append(Part.LineSegment(App.Vector(0.000000, 0.000000, 0.000000), App.Vector(0.000000, 0.003175, 0.000000)))
comp.append(Part.LineSegment(App.Vector(0.000000, 0.003175, 0.000000), App.Vector(-1.828800, 0.003175, 0.000000)))
comp.append(Part.LineSegment(App.Vector(-1.828800, 0.003175, 0.000000), App.Vector(-1.828800, -0.000000, 0.000000)))
comp.append(Part.LineSegment(App.Vector(0.000000, 0.000000, 0.000000), App.Vector(2.133600, 0.000000, 0.000000)))
comp.append(Part.LineSegment(App.Vector(2.133600, 0.000000, 0.000000), App.Vector(2.133600, 0.912813, 0.000000)))
comp.append(Part.LineSegment(App.Vector(2.133600, 0.912813, 0.000000), App.Vector(0.000000, 0.912813, 0.000000)))
comp.append(Part.LineSegment(App.Vector(0.000000, 0.912813, 0.000000), App.Vector(0.000000, 0.000000, 0.000000)))
comp.append(Part.LineSegment(App.Vector(-0.912812, -0.000000, 0.000000), App.Vector(0.000000, -0.000000, 0.000000)))
comp.append(Part.LineSegment(App.Vector(0.000000, -0.000000, 0.000000), App.Vector(0.000000, 2.133600, 0.000000)))
comp.append(Part.LineSegment(App.Vector(0.000000, 2.133600, 0.000000), App.Vector(-0.912812, 2.133600, 0.000000)))
comp.append(Part.LineSegment(App.Vector(-0.912812, 2.133600, 0.000000), App.Vector(-0.912812, -0.000000, 0.000000)))
comp.append(Part.LineSegment(App.Vector(0.000000, 0.000000, 0.000000), App.Vector(0.044450, 0.000000, 0.000000)))
comp.append(Part.LineSegment(App.Vector(0.044450, 0.000000, 0.000000), App.Vector(0.044450, 0.006350, 0.000000)))
comp.append(Part.LineSegment(App.Vector(0.044450, 0.006350, 0.000000), App.Vector(0.006350, 0.006350, 0.000000)))
comp.append(Part.LineSegment(App.Vector(0.006350, 0.006350, 0.000000), App.Vector(0.006350, 0.050800, 0.000000)))
comp.append(Part.LineSegment(App.Vector(0.006350, 0.050800, 0.000000), App.Vector(0.000000, 0.050800, 0.000000)))
comp.append(Part.LineSegment(App.Vector(0.000000, 0.050800, 0.000000), App.Vector(0.000000, 0.000000, 0.000000)))
comp.append(Part.LineSegment(App.Vector(-0.101600, -0.000000, 0.000000), App.Vector(-0.101600, 0.050800, 0.000000)))
comp.append(Part.LineSegment(App.Vector(-0.101600, 0.050800, 0.000000), App.Vector(-0.107950, 0.050800, 0.000000)))
comp.append(Part.LineSegment(App.Vector(-0.107950, 0.050800, 0.000000), App.Vector(-0.107950, 0.006350, 0.000000)))
comp.append(Part.LineSegment(App.Vector(-0.107950, 0.006350, 0.000000), App.Vector(-0.146050, 0.006350, 0.000000)))
comp.append(Part.LineSegment(App.Vector(-0.146050, 0.006350, 0.000000), App.Vector(-0.146050, -0.000000, 0.000000)))
comp.append(Part.LineSegment(App.Vector(-0.146050, -0.000000, 0.000000), App.Vector(-0.101600, -0.000000, 0.000000)))
comp.append(Part.LineSegment(App.Vector(0.000000, 0.120650, 0.000000), App.Vector(0.000000, 0.069850, 0.000000)))
comp.append(Part.LineSegment(App.Vector(0.000000, 0.069850, 0.000000), App.Vector(0.006350, 0.069850, 0.000000)))
comp.append(Part.LineSegment(App.Vector(0.006350, 0.069850, 0.000000), App.Vector(0.006350, 0.114300, 0.000000)))
comp.append(Part.LineSegment(App.Vector(0.006350, 0.114300, 0.000000), App.Vector(0.044450, 0.114300, 0.000000)))
comp.append(Part.LineSegment(App.Vector(0.044450, 0.114300, 0.000000), App.Vector(0.044450, 0.120650, 0.000000)))
comp.append(Part.LineSegment(App.Vector(0.044450, 0.120650, 0.000000), App.Vector(0.000000, 0.120650, 0.000000)))
comp.append(Part.LineSegment(App.Vector(-0.101600, 0.120650, 0.000000), App.Vector(-0.146050, 0.120650, 0.000000)))
comp.append(Part.LineSegment(App.Vector(-0.146050, 0.120650, 0.000000), App.Vector(-0.146050, 0.114300, 0.000000)))
comp.append(Part.LineSegment(App.Vector(-0.146050, 0.114300, 0.000000), App.Vector(-0.107950, 0.114300, 0.000000)))
comp.append(Part.LineSegment(App.Vector(-0.107950, 0.114300, 0.000000), App.Vector(-0.107950, 0.069850, 0.000000)))
comp.append(Part.LineSegment(App.Vector(-0.107950, 0.069850, 0.000000), App.Vector(-0.101600, 0.069850, 0.000000)))
comp.append(Part.LineSegment(App.Vector(-0.101600, 0.069850, 0.000000), App.Vector(-0.101600, 0.120650, 0.000000)))
comp.append(Part.LineSegment(App.Vector(-0.914400, 0.000000, 0.000000), App.Vector(0.000000, 0.000000, 0.000000)))
comp.append(Part.LineSegment(App.Vector(0.000000, 0.000000, 0.000000), App.Vector(0.000000, 0.012700, 0.000000)))
comp.append(Part.LineSegment(App.Vector(0.000000, 0.012700, 0.000000), App.Vector(-0.914400, 0.012700, 0.000000)))
comp.append(Part.LineSegment(App.Vector(-0.914400, 0.012700, 0.000000), App.Vector(-0.914400, 0.000000, 0.000000)))
comp.append(Part.LineSegment(App.Vector(-0.025400, 0.000000, 0.000000), App.Vector(0.000000, 0.000000, 0.000000)))
comp.append(Part.LineSegment(App.Vector(0.000000, 0.000000, 0.000000), App.Vector(0.000000, 0.228600, 0.000000)))
comp.append(Part.LineSegment(App.Vector(0.000000, 0.228600, 0.000000), App.Vector(-0.025400, 0.228600, 0.000000)))
comp.append(Part.LineSegment(App.Vector(-0.025400, 0.228600, 0.000000), App.Vector(-0.025400, 0.000000, 0.000000)))
comp.append(Part.LineSegment(App.Vector(-0.031294, 0.000000, 0.000000), App.Vector(0.000000, 0.000000, 0.000000)))
comp.append(Part.LineSegment(App.Vector(0.000000, 0.000000, 0.000000), App.Vector(0.000000, -0.050800, 0.000000)))
comp.append(Part.LineSegment(App.Vector(0.000000, -0.050800, 0.000000), App.Vector(-0.031294, -0.050800, 0.000000)))
comp.append(Part.LineSegment(App.Vector(-1.143208, 0.000000, 0.000000), App.Vector(0.000000, 0.000000, 0.000000)))
comp.append(Part.LineSegment(App.Vector(0.000000, 0.000000, 0.000000), App.Vector(0.000000, 0.050800, 0.000000)))
comp.append(Part.LineSegment(App.Vector(0.000000, 0.050800, 0.000000), App.Vector(-1.143208, 0.050800, 0.000000)))
comp.append(Part.LineSegment(App.Vector(-1.143208, 0.050800, 0.000000), App.Vector(-1.143208, 0.000000, 0.000000)))
comp.append(Part.LineSegment(App.Vector(0.000000, -0.009525, 0.000000), App.Vector(-0.000000, 0.009525, 0.000000)))
comp.append(Part.LineSegment(App.Vector(-0.000000, 0.009525, 0.000000), App.Vector(0.004750, 0.009525, 0.000000)))
comp.append(Part.LineSegment(App.Vector(0.004750, 0.009525, 0.000000), App.Vector(0.004750, -0.009525, 0.000000)))
comp.append(Part.LineSegment(App.Vector(0.004750, -0.009525, 0.000000), App.Vector(0.000000, -0.009525, 0.000000)))
comp.append(Part.LineSegment(App.Vector(0.017463, -0.000000, 0.000000), App.Vector(0.017463, -0.004763, 0.000000)))
comp.append(Part.LineSegment(App.Vector(0.017463, -0.004763, 0.000000), App.Vector(0.004763, -0.004762, 0.000000)))
comp.append(Part.LineSegment(App.Vector(0.004763, -0.004763, 0.000000), App.Vector(0.004763, -0.000000, 0.000000)))
comp.append(Part.LineSegment(App.Vector(0.004763, -0.000000, 0.000000), App.Vector(0.017463, -0.000000, 0.000000)))
comp.append(Part.LineSegment(App.Vector(0.000000, -0.009525, 0.000000), App.Vector(-0.004750, -0.009525, 0.000000)))
comp.append(Part.LineSegment(App.Vector(-0.004750, -0.009525, 0.000000), App.Vector(-0.004750, 0.009525, 0.000000)))
comp.append(Part.LineSegment(App.Vector(-0.004750, 0.009525, 0.000000), App.Vector(0.000000, 0.009525, 0.000000)))
comp.append(Part.LineSegment(App.Vector(0.000000, 0.009525, 0.000000), App.Vector(0.000000, -0.009525, 0.000000)))
comp.append(Part.LineSegment(App.Vector(-0.004750, 0.004763, 0.000000), App.Vector(-0.004750, 0.000000, 0.000000)))
comp.append(Part.LineSegment(App.Vector(-0.004750, 0.000000, 0.000000), App.Vector(-0.017450, 0.000000, 0.000000)))
comp.append(Part.LineSegment(App.Vector(-0.017450, 0.000000, 0.000000), App.Vector(-0.017450, 0.004763, 0.000000)))
comp.append(Part.LineSegment(App.Vector(-0.017450, 0.004763, 0.000000), App.Vector(-0.004750, 0.004763, 0.000000)))
comp.append(Part.LineSegment(App.Vector(0.000000, 0.101699, 0.000000), App.Vector(0.000000, 0.000099, 0.000000)))
comp.append(Part.LineSegment(App.Vector(0.000000, 0.000099, 0.000000), App.Vector(-0.003175, 0.000099, 0.000000)))
comp.append(Part.LineSegment(App.Vector(-0.003175, 0.000099, 0.000000), App.Vector(-0.003175, 0.101699, 0.000000)))
comp.append(Part.LineSegment(App.Vector(-0.003175, 0.101699, 0.000000), App.Vector(0.000000, 0.101699, 0.000000)))
comp.append(Part.LineSegment(App.Vector(-0.751513, -0.000000, 0.000000), App.Vector(0.089040, -0.000000, 0.000000)))
comp.append(Part.LineSegment(App.Vector(0.089040, -0.000000, 0.000000), App.Vector(0.081944, 0.203200, 0.000000)))
comp.append(Part.LineSegment(App.Vector(0.081944, 0.203200, 0.000000), App.Vector(-0.697038, 0.203200, 0.000000)))
comp.append(Part.LineSegment(App.Vector(-0.766846, 0.130912, 0.000000), App.Vector(-0.765832, 0.101889, 0.000000)))
comp.append(Part.LineSegment(App.Vector(-0.765832, 0.101889, 0.000000), App.Vector(-0.751513, -0.000000, 0.000000)))
comp.append(Part.LineSegment(App.Vector(3.028446, 4.291134, 0.000000), App.Vector(3.028446, 3.377121, 0.000000)))
comp.append(Part.LineSegment(App.Vector(-0.367084, 0.038795, 0.000000), App.Vector(-0.367084, -0.995288, 0.000000)))
comp.append(Part.LineSegment(App.Vector(-0.305300, 0.000000, 0.000000), App.Vector(0.000000, 0.000000, 0.000000)))
comp.append(Part.LineSegment(App.Vector(0.000000, 0.000000, 0.000000), App.Vector(0.000000, 0.015400, 0.000000)))
comp.append(Part.LineSegment(App.Vector(0.000000, 0.015400, 0.000000), App.Vector(-0.147700, 0.015400, 0.000000)))
comp.append(Part.LineSegment(App.Vector(-0.147700, 0.015400, 0.000000), App.Vector(-0.147700, 0.292500, 0.000000)))
comp.append(Part.LineSegment(App.Vector(-0.147700, 0.292500, 0.000000), App.Vector(0.000000, 0.292500, 0.000000)))
comp.append(Part.LineSegment(App.Vector(0.000000, 0.292500, 0.000000), App.Vector(0.000000, 0.307900, 0.000000)))
comp.append(Part.LineSegment(App.Vector(0.000000, 0.307900, 0.000000), App.Vector(-0.305300, 0.307900, 0.000000)))
comp.append(Part.LineSegment(App.Vector(-0.305300, 0.307900, 0.000000), App.Vector(-0.305300, 0.292500, 0.000000)))
comp.append(Part.LineSegment(App.Vector(-0.305300, 0.292500, 0.000000), App.Vector(-0.157600, 0.292500, 0.000000)))
comp.append(Part.LineSegment(App.Vector(-0.157600, 0.292500, 0.000000), App.Vector(-0.157600, 0.015400, 0.000000)))
comp.append(Part.LineSegment(App.Vector(-0.157600, 0.015400, 0.000000), App.Vector(-0.305300, 0.015400, 0.000000)))
comp.append(Part.LineSegment(App.Vector(-0.305300, 0.015400, 0.000000), App.Vector(-0.305300, 0.000000, 0.000000)))
comp.append(Part.LineSegment(App.Vector(0.000000, 0.015400, 0.000000), App.Vector(-0.132500, 0.015400, 0.000000)))
comp.append(Part.LineSegment(App.Vector(-0.147700, 0.030600, 0.000000), App.Vector(-0.147700, 0.277300, 0.000000)))
comp.append(Part.LineSegment(App.Vector(-0.132500, 0.292500, 0.000000), App.Vector(0.000000, 0.292500, 0.000000)))
comp.append(Part.LineSegment(App.Vector(-0.305300, 0.292500, 0.000000), App.Vector(-0.172800, 0.292500, 0.000000)))
comp.append(Part.LineSegment(App.Vector(-0.157600, 0.277300, 0.000000), App.Vector(-0.157600, 0.030600, 0.000000)))
comp.append(Part.LineSegment(App.Vector(-0.172800, 0.015400, 0.000000), App.Vector(-0.305300, 0.015400, 0.000000)))
comp.append(Part.LineSegment(App.Vector(-0.381000, 0.000000, 0.000000), App.Vector(0.000000, 0.000000, 0.000000)))
comp.append(Part.LineSegment(App.Vector(0.025400, 0.025400, 0.000000), App.Vector(0.025400, 0.368300, 0.000000)))
comp.append(Part.LineSegment(App.Vector(0.000000, 0.393700, 0.000000), App.Vector(-0.381000, 0.393700, 0.000000)))
comp.append(Part.LineSegment(App.Vector(-0.406400, 0.368300, 0.000000), App.Vector(-0.406400, 0.025400, 0.000000)))
comp.append(Part.LineSegment(App.Vector(0.025400, 0.025400, 0.000000), App.Vector(0.025400, 0.254000, 0.000000)))
comp.append(Part.LineSegment(App.Vector(0.000000, 0.279400, 0.000000), App.Vector(-0.381000, 0.279400, 0.000000)))
comp.append(Part.LineSegment(App.Vector(-0.406400, 0.254000, 0.000000), App.Vector(-0.406400, 0.025400, 0.000000)))
comp.append(Part.LineSegment(App.Vector(0.000000, 0.000000, 0.000000), App.Vector(0.152400, 0.000000, 0.000000)))
comp.append(Part.LineSegment(App.Vector(0.152400, 0.000000, 0.000000), App.Vector(0.152400, 0.025400, 0.000000)))
comp.append(Part.LineSegment(App.Vector(0.152400, 0.025400, 0.000000), App.Vector(0.000000, 0.025400, 0.000000)))
comp.append(Part.LineSegment(App.Vector(0.000000, 0.025400, 0.000000), App.Vector(0.000000, 0.000000, 0.000000)))
comp.append(Part.LineSegment(App.Vector(0.000000, -0.076200, 0.000000), App.Vector(0.152400, -0.076200, 0.000000)))
comp.append(Part.LineSegment(App.Vector(0.152400, -0.076200, 0.000000), App.Vector(0.152400, -0.050800, 0.000000)))
comp.append(Part.LineSegment(App.Vector(0.152400, -0.050800, 0.000000), App.Vector(0.000000, -0.050800, 0.000000)))
comp.append(Part.LineSegment(App.Vector(0.000000, -0.050800, 0.000000), App.Vector(0.000000, -0.076200, 0.000000)))
comp.append(Part.LineSegment(App.Vector(3.657600, -0.076200, 0.000000), App.Vector(3.810000, -0.076200, 0.000000)))
comp.append(Part.LineSegment(App.Vector(3.810000, -0.076200, 0.000000), App.Vector(3.810000, -0.050800, 0.000000)))
comp.append(Part.LineSegment(App.Vector(3.810000, -0.050800, 0.000000), App.Vector(3.657600, -0.050800, 0.000000)))
comp.append(Part.LineSegment(App.Vector(3.657600, -0.050800, 0.000000), App.Vector(3.657600, -0.076200, 0.000000)))
comp.append(Part.LineSegment(App.Vector(3.657600, 0.000000, 0.000000), App.Vector(3.810000, 0.000000, 0.000000)))
comp.append(Part.LineSegment(App.Vector(3.810000, 0.000000, 0.000000), App.Vector(3.810000, 0.025400, 0.000000)))
comp.append(Part.LineSegment(App.Vector(3.810000, 0.025400, 0.000000), App.Vector(3.657600, 0.025400, 0.000000)))
comp.append(Part.LineSegment(App.Vector(3.657600, 0.025400, 0.000000), App.Vector(3.657600, 0.000000, 0.000000)))
comp.append(Part.LineSegment(App.Vector(7.315200, -0.076200, 0.000000), App.Vector(7.467600, -0.076200, 0.000000)))
comp.append(Part.LineSegment(App.Vector(7.467600, -0.076200, 0.000000), App.Vector(7.467600, -0.050800, 0.000000)))
comp.append(Part.LineSegment(App.Vector(7.467600, -0.050800, 0.000000), App.Vector(7.315200, -0.050800, 0.000000)))
comp.append(Part.LineSegment(App.Vector(7.315200, -0.050800, 0.000000), App.Vector(7.315200, -0.076200, 0.000000)))
comp.append(Part.LineSegment(App.Vector(7.315200, 0.000000, 0.000000), App.Vector(7.467600, 0.000000, 0.000000)))
comp.append(Part.LineSegment(App.Vector(7.467600, 0.000000, 0.000000), App.Vector(7.467600, 0.025400, 0.000000)))
comp.append(Part.LineSegment(App.Vector(7.467600, 0.025400, 0.000000), App.Vector(7.315200, 0.025400, 0.000000)))
comp.append(Part.LineSegment(App.Vector(7.315200, 0.025400, 0.000000), App.Vector(7.315200, 0.000000, 0.000000)))
comp.append(Part.LineSegment(App.Vector(-0.301625, 0.000000, 0.000000), App.Vector(-0.053975, 0.000000, 0.000000)))
comp.append(Part.LineSegment(App.Vector(0.000000, 0.053975, 0.000000), App.Vector(0.000000, 0.200025, 0.000000)))
comp.append(Part.LineSegment(App.Vector(-0.053975, 0.254000, 0.000000), App.Vector(-0.301625, 0.254000, 0.000000)))
comp.append(Part.LineSegment(App.Vector(-0.355600, 0.200025, 0.000000), App.Vector(-0.355600, 0.053975, 0.000000)))
comp.append(Part.LineSegment(App.Vector(-0.241300, 0.000000, 0.000000), App.Vector(0.000000, 0.000000, 0.000000)))
comp.append(Part.LineSegment(App.Vector(0.050800, 0.050800, 0.000000), App.Vector(0.050800, 0.190500, 0.000000)))
comp.append(Part.LineSegment(App.Vector(0.000000, 0.241300, 0.000000), App.Vector(-0.241300, 0.241300, 0.000000)))
comp.append(Part.LineSegment(App.Vector(-0.292100, 0.190500, 0.000000), App.Vector(-0.292100, 0.050800, 0.000000)))
comp.append(Part.LineSegment(App.Vector(-0.076000, 0.076000, 0.000000), App.Vector(-0.076000, -1.906000, 0.000000)))
comp.append(Part.LineSegment(App.Vector(-0.076000, -1.906000, 0.000000), App.Vector(2.134000, -1.906000, 0.000000)))
comp.append(Part.LineSegment(App.Vector(2.134000, -1.906000, 0.000000), App.Vector(2.134000, -1.830000, 0.000000)))
comp.append(Part.LineSegment(App.Vector(2.134000, -1.830000, 0.000000), App.Vector(0.000000, -1.830000, 0.000000)))
comp.append(Part.LineSegment(App.Vector(0.000000, -1.830000, 0.000000), App.Vector(0.000000, 0.000000, 0.000000)))
comp.append(Part.LineSegment(App.Vector(-0.915000, 0.000000, 0.000000), App.Vector(0.000000, 0.000000, 0.000000)))
comp.append(Part.LineSegment(App.Vector(0.000000, 2.134000, 0.000000), App.Vector(-0.915000, 2.134000, 0.000000)))
comp.append(Part.LineSegment(App.Vector(-0.915000, 2.134000, 0.000000), App.Vector(-0.915000, 0.000000, 0.000000)))
comp.append(Part.LineSegment(App.Vector(-0.610000, -0.000000, 0.000000), App.Vector(0.000000, 0.000000, 0.000000)))
comp.append(Part.LineSegment(App.Vector(0.000000, 0.000000, 0.000000), App.Vector(0.000000, 1.220000, 0.000000)))
comp.append(Part.LineSegment(App.Vector(0.000000, 1.220000, 0.000000), App.Vector(-0.610000, 1.220000, 0.000000)))
comp.append(Part.LineSegment(App.Vector(-0.610000, 1.220000, 0.000000), App.Vector(-0.610000, -0.000000, 0.000000)))
comp.append(Part.LineSegment(App.Vector(-0.578000, 0.032000, 0.000000), App.Vector(-0.578000, 1.188000, 0.000000)))
comp.append(Part.LineSegment(App.Vector(-0.578000, 1.188000, 0.000000), App.Vector(-0.032000, 1.188000, 0.000000)))
comp.append(Part.LineSegment(App.Vector(-0.032000, 1.188000, 0.000000), App.Vector(-0.032000, 0.032000, 0.000000)))
comp.append(Part.LineSegment(App.Vector(-0.032000, 0.032000, 0.000000), App.Vector(-0.578000, 0.032000, 0.000000)))
comp.append(Part.LineSegment(App.Vector(-0.591000, 0.019000, 0.000000), App.Vector(-0.591000, 1.201000, 0.000000)))
comp.append(Part.LineSegment(App.Vector(-0.591000, 1.201000, 0.000000), App.Vector(-0.019000, 1.201000, 0.000000)))
comp.append(Part.LineSegment(App.Vector(-0.019000, 1.201000, 0.000000), App.Vector(-0.019000, 0.019000, 0.000000)))
comp.append(Part.LineSegment(App.Vector(-0.019000, 0.019000, 0.000000), App.Vector(-0.591000, 0.019000, 0.000000)))
comp.append(Part.LineSegment(App.Vector(-0.572000, -0.000000, 0.000000), App.Vector(0.000000, 0.000000, 0.000000)))
comp.append(Part.LineSegment(App.Vector(0.000000, 0.000000, 0.000000), App.Vector(0.000000, 1.182000, 0.000000)))
comp.append(Part.LineSegment(App.Vector(0.000000, 1.182000, 0.000000), App.Vector(-0.572000, 1.182000, 0.000000)))
comp.append(Part.LineSegment(App.Vector(-0.572000, 1.182000, 0.000000), App.Vector(-0.572000, -0.000000, 0.000000)))
comp.append(Part.LineSegment(App.Vector(-0.528000, 0.044000, 0.000000), App.Vector(-0.528000, 1.138000, 0.000000)))
comp.append(Part.LineSegment(App.Vector(-0.528000, 1.138000, 0.000000), App.Vector(-0.044000, 1.138000, 0.000000)))
comp.append(Part.LineSegment(App.Vector(-0.044000, 1.138000, 0.000000), App.Vector(-0.044000, 0.044000, 0.000000)))
comp.append(Part.LineSegment(App.Vector(-0.044000, 0.044000, 0.000000), App.Vector(-0.528000, 0.044000, 0.000000)))
comp.append(Part.LineSegment(App.Vector(-0.484000, -0.000000, 0.000000), App.Vector(0.000000, 0.000000, 0.000000)))
comp.append(Part.LineSegment(App.Vector(0.000000, 0.000000, 0.000000), App.Vector(0.000000, 1.094000, 0.000000)))
comp.append(Part.LineSegment(App.Vector(0.000000, 1.094000, 0.000000), App.Vector(-0.484000, 1.094000, 0.000000)))
comp.append(Part.LineSegment(App.Vector(-0.484000, 1.094000, 0.000000), App.Vector(-0.484000, -0.000000, 0.000000)))
comp.append(Part.LineSegment(App.Vector(-0.025000, 0.000000, 0.000000), App.Vector(0.000000, 0.000000, 0.000000)))
comp.append(Part.LineSegment(App.Vector(0.000000, 0.000000, 0.000000), App.Vector(0.000000, 0.025000, 0.000000)))
comp.append(Part.LineSegment(App.Vector(0.000000, 0.025000, 0.000000), App.Vector(-0.025000, 0.025000, 0.000000)))
comp.append(Part.LineSegment(App.Vector(-0.025000, 0.025000, 0.000000), App.Vector(-0.025000, 0.000000, 0.000000)))
comp.append(Part.LineSegment(App.Vector(0.000000, 0.000000, 0.000000), App.Vector(0.032000, 0.000000, 0.000000)))
comp.append(Part.LineSegment(App.Vector(0.032000, 0.000000, 0.000000), App.Vector(0.032000, 0.006500, 0.000000)))
comp.append(Part.LineSegment(App.Vector(0.032000, 0.006500, 0.000000), App.Vector(0.006500, 0.006500, 0.000000)))
comp.append(Part.LineSegment(App.Vector(0.006500, 0.006500, 0.000000), App.Vector(0.006500, 0.032000, 0.000000)))
comp.append(Part.LineSegment(App.Vector(0.006500, 0.032000, 0.000000), App.Vector(0.000000, 0.032000, 0.000000)))
comp.append(Part.LineSegment(App.Vector(0.000000, 0.032000, 0.000000), App.Vector(0.000000, 0.000000, 0.000000)))
comp.append(Part.LineSegment(App.Vector(0.000000, -0.009500, 0.000000), App.Vector(0.000000, -0.041500, 0.000000)))
comp.append(Part.LineSegment(App.Vector(0.000000, -0.041500, 0.000000), App.Vector(0.006500, -0.041500, 0.000000)))
comp.append(Part.LineSegment(App.Vector(0.006500, -0.041500, 0.000000), App.Vector(0.006500, -0.016000, 0.000000)))
comp.append(Part.LineSegment(App.Vector(0.006500, -0.016000, 0.000000), App.Vector(0.032000, -0.016000, 0.000000)))
comp.append(Part.LineSegment(App.Vector(0.032000, -0.016000, 0.000000), App.Vector(0.032000, -0.009500, 0.000000)))
comp.append(Part.LineSegment(App.Vector(0.032000, -0.009500, 0.000000), App.Vector(0.000000, -0.009500, 0.000000)))
comp.append(Part.LineSegment(App.Vector(-0.009500, 0.000000, 0.000000), App.Vector(-0.009500, 0.032000, 0.000000)))
comp.append(Part.LineSegment(App.Vector(-0.009500, 0.032000, 0.000000), App.Vector(-0.016000, 0.032000, 0.000000)))
comp.append(Part.LineSegment(App.Vector(-0.016000, 0.032000, 0.000000), App.Vector(-0.016000, 0.006500, 0.000000)))
comp.append(Part.LineSegment(App.Vector(-0.016000, 0.006500, 0.000000), App.Vector(-0.041500, 0.006500, 0.000000)))
comp.append(Part.LineSegment(App.Vector(-0.041500, 0.006500, 0.000000), App.Vector(-0.041500, 0.000000, 0.000000)))
comp.append(Part.LineSegment(App.Vector(-0.041500, 0.000000, 0.000000), App.Vector(-0.009500, 0.000000, 0.000000)))
comp.append(Part.LineSegment(App.Vector(-0.032000, 0.000000, 0.000000), App.Vector(0.000000, 0.000000, 0.000000)))
comp.append(Part.LineSegment(App.Vector(0.000000, 0.000000, 0.000000), App.Vector(0.000000, 0.006500, 0.000000)))
comp.append(Part.LineSegment(App.Vector(0.000000, 0.006500, 0.000000), App.Vector(-0.025500, 0.006500, 0.000000)))
comp.append(Part.LineSegment(App.Vector(-0.025500, 0.006500, 0.000000), App.Vector(-0.025500, 0.031500, 0.000000)))
comp.append(Part.LineSegment(App.Vector(-0.025500, 0.031500, 0.000000), App.Vector(-0.032000, 0.031500, 0.000000)))
comp.append(Part.LineSegment(App.Vector(-0.032000, 0.031500, 0.000000), App.Vector(-0.032000, 0.000000, 0.000000)))
comp.append(Part.LineSegment(App.Vector(-0.041500, 0.000000, 0.000000), App.Vector(-0.041500, 0.031500, 0.000000)))
comp.append(Part.LineSegment(App.Vector(-0.041500, 0.031500, 0.000000), App.Vector(-0.048000, 0.031500, 0.000000)))
comp.append(Part.LineSegment(App.Vector(-0.048000, 0.031500, 0.000000), App.Vector(-0.048000, 0.006500, 0.000000)))
comp.append(Part.LineSegment(App.Vector(-0.048000, 0.006500, 0.000000), App.Vector(-0.073500, 0.006500, 0.000000)))
comp.append(Part.LineSegment(App.Vector(-0.073500, 0.006500, 0.000000), App.Vector(-0.073500, 0.000000, 0.000000)))
comp.append(Part.LineSegment(App.Vector(-0.073500, 0.000000, 0.000000), App.Vector(-0.041500, 0.000000, 0.000000)))
comp.append(Part.LineSegment(App.Vector(0.000000, 0.000000, 0.000000), App.Vector(0.031500, 0.000000, 0.000000)))
comp.append(Part.LineSegment(App.Vector(0.031500, 0.000000, 0.000000), App.Vector(0.031500, 0.006500, 0.000000)))
comp.append(Part.LineSegment(App.Vector(0.031500, 0.006500, 0.000000), App.Vector(0.006500, 0.006500, 0.000000)))
comp.append(Part.LineSegment(App.Vector(0.006500, -0.016000, 0.000000), App.Vector(0.031500, -0.016000, 0.000000)))
comp.append(Part.LineSegment(App.Vector(0.031500, -0.016000, 0.000000), App.Vector(0.031500, -0.009500, 0.000000)))
comp.append(Part.LineSegment(App.Vector(0.031500, -0.009500, 0.000000), App.Vector(-0.000000, -0.009500, 0.000000)))
comp.append(Part.LineSegment(App.Vector(0.000000, 0.000000, 0.000000), App.Vector(0.609600, 0.000000, 0.000000)))
comp.append(Part.LineSegment(App.Vector(0.609600, 0.000000, 0.000000), App.Vector(0.609600, 0.609600, 0.000000)))
comp.append(Part.LineSegment(App.Vector(0.609600, 0.609600, 0.000000), App.Vector(0.000000, 0.609600, 0.000000)))
comp.append(Part.LineSegment(App.Vector(0.000000, 0.609600, 0.000000), App.Vector(0.000000, 0.000000, 0.000000)))
comp.append(Part.LineSegment(App.Vector(-0.050800, 0.000000, 0.000000), App.Vector(0.000000, 0.000000, 0.000000)))
comp.append(Part.LineSegment(App.Vector(0.000000, 0.050800, 0.000000), App.Vector(-0.050800, 0.050800, 0.000000)))
comp.append(Part.LineSegment(App.Vector(-0.050800, 0.050800, 0.000000), App.Vector(-0.050800, 0.000000, 0.000000)))
comp.append(Part.LineSegment(App.Vector(-0.050800, 0.355600, 0.000000), App.Vector(-0.000000, 0.355600, 0.000000)))
comp.append(Part.LineSegment(App.Vector(-0.000000, 0.355600, 0.000000), App.Vector(-0.000000, 0.406400, 0.000000)))
comp.append(Part.LineSegment(App.Vector(-0.000000, 0.406400, 0.000000), App.Vector(-0.050800, 0.406400, 0.000000)))
comp.append(Part.LineSegment(App.Vector(-0.050800, 0.406400, 0.000000), App.Vector(-0.050800, 0.355600, 0.000000)))
comp.append(Part.LineSegment(App.Vector(-0.406400, 0.000000, 0.000000), App.Vector(-0.355600, 0.000000, 0.000000)))
comp.append(Part.LineSegment(App.Vector(-0.355600, 0.000000, 0.000000), App.Vector(-0.355600, 0.050800, 0.000000)))
comp.append(Part.LineSegment(App.Vector(-0.355600, 0.050800, 0.000000), App.Vector(-0.406400, 0.050800, 0.000000)))
comp.append(Part.LineSegment(App.Vector(-0.406400, 0.050800, 0.000000), App.Vector(-0.406400, 0.000000, 0.000000)))
comp.append(Part.LineSegment(App.Vector(-0.406400, 0.355600, 0.000000), App.Vector(-0.355600, 0.355600, 0.000000)))
comp.append(Part.LineSegment(App.Vector(-0.355600, 0.355600, 0.000000), App.Vector(-0.355600, 0.406400, 0.000000)))
comp.append(Part.LineSegment(App.Vector(-0.355600, 0.406400, 0.000000), App.Vector(-0.406400, 0.406400, 0.000000)))
comp.append(Part.LineSegment(App.Vector(-0.406400, 0.406400, 0.000000), App.Vector(-0.406400, 0.355600, 0.000000)))
comp.append(Part.LineSegment(App.Vector(0.000000, -0.050800, 0.000000), App.Vector(0.304800, -0.050800, 0.000000)))
comp.append(Part.LineSegment(App.Vector(0.304800, -0.050800, 0.000000), App.Vector(0.304800, 0.000000, 0.000000)))
comp.append(Part.LineSegment(App.Vector(0.304800, 0.000000, 0.000000), App.Vector(0.355600, 0.000000, 0.000000)))
comp.append(Part.LineSegment(App.Vector(0.355600, 0.000000, 0.000000), App.Vector(0.355600, 0.304800, 0.000000)))
comp.append(Part.LineSegment(App.Vector(0.355600, 0.304800, 0.000000), App.Vector(0.304800, 0.304800, 0.000000)))
comp.append(Part.LineSegment(App.Vector(0.304800, 0.304800, 0.000000), App.Vector(0.304800, 0.355600, 0.000000)))
comp.append(Part.LineSegment(App.Vector(0.304800, 0.355600, 0.000000), App.Vector(0.000000, 0.355600, 0.000000)))
comp.append(Part.LineSegment(App.Vector(0.000000, 0.355600, 0.000000), App.Vector(0.000000, 0.304800, 0.000000)))
comp.append(Part.LineSegment(App.Vector(0.000000, 0.304800, 0.000000), App.Vector(-0.050800, 0.304800, 0.000000)))
comp.append(Part.LineSegment(App.Vector(-0.050800, 0.304800, 0.000000), App.Vector(-0.050800, 0.000000, 0.000000)))
comp.append(Part.LineSegment(App.Vector(-0.292100, 0.000000, 0.000000), App.Vector(0.000000, 0.000000, 0.000000)))
comp.append(Part.LineSegment(App.Vector(0.000000, 0.000000, 0.000000), App.Vector(0.000000, 0.292100, 0.000000)))
comp.append(Part.LineSegment(App.Vector(0.000000, 0.292100, 0.000000), App.Vector(-0.292100, 0.292100, 0.000000)))
comp.append(Part.LineSegment(App.Vector(-0.292100, 0.292100, 0.000000), App.Vector(-0.292100, 0.000000, 0.000000)))
comp.append(Part.LineSegment(App.Vector(-0.202000, 0.000000, 0.000000), App.Vector(0.000000, 0.000000, 0.000000)))
comp.append(Part.LineSegment(App.Vector(0.000000, 0.000000, 0.000000), App.Vector(0.000000, 0.011000, 0.000000)))
comp.append(Part.LineSegment(App.Vector(0.000000, 0.011000, 0.000000), App.Vector(-0.097300, 0.011000, 0.000000)))
comp.append(Part.LineSegment(App.Vector(-0.097300, 0.011000, 0.000000), App.Vector(-0.097300, 0.236000, 0.000000)))
comp.append(Part.LineSegment(App.Vector(-0.097300, 0.236000, 0.000000), App.Vector(0.000000, 0.236000, 0.000000)))
comp.append(Part.LineSegment(App.Vector(0.000000, 0.236000, 0.000000), App.Vector(0.000000, 0.247000, 0.000000)))
comp.append(Part.LineSegment(App.Vector(0.000000, 0.247000, 0.000000), App.Vector(-0.202000, 0.247000, 0.000000)))
comp.append(Part.LineSegment(App.Vector(-0.202000, 0.247000, 0.000000), App.Vector(-0.202000, 0.236000, 0.000000)))
comp.append(Part.LineSegment(App.Vector(-0.202000, 0.236000, 0.000000), App.Vector(-0.104700, 0.236000, 0.000000)))
comp.append(Part.LineSegment(App.Vector(-0.104700, 0.236000, 0.000000), App.Vector(-0.104700, 0.011000, 0.000000)))
comp.append(Part.LineSegment(App.Vector(-0.104700, 0.011000, 0.000000), App.Vector(-0.202000, 0.011000, 0.000000)))
comp.append(Part.LineSegment(App.Vector(-0.202000, 0.011000, 0.000000), App.Vector(-0.202000, 0.000000, 0.000000)))
comp.append(Part.LineSegment(App.Vector(0.000000, 0.011000, 0.000000), App.Vector(-0.080300, 0.011000, 0.000000)))
comp.append(Part.LineSegment(App.Vector(-0.097300, 0.028000, 0.000000), App.Vector(-0.097300, 0.219000, 0.000000)))
comp.append(Part.LineSegment(App.Vector(-0.080300, 0.236000, 0.000000), App.Vector(0.000000, 0.236000, 0.000000)))
comp.append(Part.LineSegment(App.Vector(-0.202000, 0.236000, 0.000000), App.Vector(-0.121700, 0.236000, 0.000000)))
comp.append(Part.LineSegment(App.Vector(-0.104700, 0.219000, 0.000000), App.Vector(-0.104700, 0.028000, 0.000000)))
comp.append(Part.LineSegment(App.Vector(-0.121700, 0.011000, 0.000000), App.Vector(-0.202000, 0.011000, 0.000000)))
comp.append(Part.LineSegment(App.Vector(-0.406400, 0.000000, 0.000000), App.Vector(0.000000, 0.000000, 0.000000)))
comp.append(Part.LineSegment(App.Vector(0.000000, 0.000000, 0.000000), App.Vector(0.000000, 0.762000, 0.000000)))
comp.append(Part.LineSegment(App.Vector(0.000000, 0.762000, 0.000000), App.Vector(-1.525000, 0.762000, 0.000000)))
comp.append(Part.LineSegment(App.Vector(-1.525000, 0.762000, 0.000000), App.Vector(-1.525000, -0.000000, 0.000000)))
comp.append(Part.LineSegment(App.Vector(-1.525000, -0.000000, 0.000000), App.Vector(-1.118600, -0.000000, 0.000000)))
comp.append(Part.LineSegment(App.Vector(-1.118600, -0.000000, 0.000000), App.Vector(-1.118600, 0.635000, 0.000000)))
comp.append(Part.LineSegment(App.Vector(-1.118600, 0.635000, 0.000000), App.Vector(-0.406400, 0.635000, 0.000000)))
comp.append(Part.LineSegment(App.Vector(-0.406400, 0.635000, 0.000000), App.Vector(-0.406400, 0.000000, 0.000000)))
comp.append(Part.LineSegment(App.Vector(-1.563100, 0.000000, 0.000000), App.Vector(0.000000, 0.000000, 0.000000)))
comp.append(Part.LineSegment(App.Vector(0.000000, 0.000000, 0.000000), App.Vector(-0.000000, 0.800100, 0.000000)))
comp.append(Part.LineSegment(App.Vector(-0.000000, 0.800100, 0.000000), App.Vector(-1.563100, 0.800100, 0.000000)))
comp.append(Part.LineSegment(App.Vector(-1.563100, 0.800100, 0.000000), App.Vector(-1.563100, 0.000000, 0.000000)))
comp.append(Part.LineSegment(App.Vector(-0.368300, -0.000000, 0.000000), App.Vector(0.000000, 0.000000, 0.000000)))
comp.append(Part.LineSegment(App.Vector(0.000000, 0.000000, 0.000000), App.Vector(0.000000, 0.102000, 0.000000)))
comp.append(Part.LineSegment(App.Vector(0.000000, 0.102000, 0.000000), App.Vector(-0.368300, 0.102000, 0.000000)))
comp.append(Part.LineSegment(App.Vector(-0.368300, 0.102000, 0.000000), App.Vector(-0.368300, -0.000000, 0.000000)))
comp.append(Part.LineSegment(App.Vector(0.000000, 0.362350, 0.000000), App.Vector(0.000000, 0.533800, 0.000000)))
comp.append(Part.LineSegment(App.Vector(0.000000, 0.533800, 0.000000), App.Vector(-0.368300, 0.533800, 0.000000)))
comp.append(Part.LineSegment(App.Vector(-0.368300, 0.533800, 0.000000), App.Vector(-0.368300, 0.362350, 0.000000)))
comp.append(Part.LineSegment(App.Vector(-0.368300, 0.362350, 0.000000), App.Vector(0.000000, 0.362350, 0.000000)))
comp.append(Part.LineSegment(App.Vector(0.000000, 0.121050, 0.000000), App.Vector(0.000000, 0.222650, 0.000000)))
comp.append(Part.LineSegment(App.Vector(0.000000, 0.222650, 0.000000), App.Vector(-0.368300, 0.222650, 0.000000)))
comp.append(Part.LineSegment(App.Vector(-0.368300, 0.222650, 0.000000), App.Vector(-0.368300, 0.121050, 0.000000)))
comp.append(Part.LineSegment(App.Vector(-0.368300, 0.121050, 0.000000), App.Vector(0.000000, 0.121050, 0.000000)))
comp.append(Part.LineSegment(App.Vector(0.000000, 0.241700, 0.000000), App.Vector(0.000000, 0.343300, 0.000000)))
comp.append(Part.LineSegment(App.Vector(0.000000, 0.343300, 0.000000), App.Vector(-0.368300, 0.343300, 0.000000)))
comp.append(Part.LineSegment(App.Vector(-0.368300, 0.343300, 0.000000), App.Vector(-0.368300, 0.241700, 0.000000)))
comp.append(Part.LineSegment(App.Vector(-0.368300, 0.241700, 0.000000), App.Vector(0.000000, 0.241700, 0.000000)))
comp.append(Part.LineSegment(App.Vector(0.000000, 0.000000, 0.000000), App.Vector(0.101600, -0.000000, 0.000000)))
comp.append(Part.LineSegment(App.Vector(0.101600, -0.000000, 0.000000), App.Vector(0.101600, 0.368300, 0.000000)))
comp.append(Part.LineSegment(App.Vector(0.101600, 0.368300, 0.000000), App.Vector(0.000000, 0.368300, 0.000000)))
comp.append(Part.LineSegment(App.Vector(0.000000, 0.368300, 0.000000), App.Vector(0.000000, 0.000000, 0.000000)))
comp.append(Part.LineSegment(App.Vector(0.120650, 0.368300, 0.000000), App.Vector(0.120650, -0.000000, 0.000000)))
comp.append(Part.LineSegment(App.Vector(0.120650, -0.000000, 0.000000), App.Vector(0.533800, -0.000000, 0.000000)))
comp.append(Part.LineSegment(App.Vector(0.533800, -0.000000, 0.000000), App.Vector(0.533800, 0.368300, 0.000000)))
comp.append(Part.LineSegment(App.Vector(0.533800, 0.368300, 0.000000), App.Vector(0.120650, 0.368300, 0.000000)))
comp.append(Part.LineSegment(App.Vector(-0.304800, 0.660430, 0.000000), App.Vector(-0.304800, 0.666780, 0.000000)))
comp.append(Part.LineSegment(App.Vector(-0.304800, 0.666780, 0.000000), App.Vector(-0.292100, 0.666780, 0.000000)))
comp.append(Part.LineSegment(App.Vector(-0.292100, 0.666780, 0.000000), App.Vector(-0.292100, 0.660430, 0.000000)))
comp.append(Part.LineSegment(App.Vector(-0.292100, 0.660430, 0.000000), App.Vector(-0.304800, 0.660430, 0.000000)))
comp.append(Part.LineSegment(App.Vector(-0.425450, 0.660430, 0.000000), App.Vector(-0.425450, 0.666780, 0.000000)))
comp.append(Part.LineSegment(App.Vector(-0.425450, 0.666780, 0.000000), App.Vector(-0.412750, 0.666780, 0.000000)))
comp.append(Part.LineSegment(App.Vector(-0.412750, 0.666780, 0.000000), App.Vector(-0.412750, 0.660430, 0.000000)))
comp.append(Part.LineSegment(App.Vector(-0.412750, 0.660430, 0.000000), App.Vector(-0.425450, 0.660430, 0.000000)))
comp.append(Part.LineSegment(App.Vector(-0.546100, 0.660430, 0.000000), App.Vector(-0.546100, 0.666780, 0.000000)))
comp.append(Part.LineSegment(App.Vector(-0.546100, 0.666780, 0.000000), App.Vector(-0.533400, 0.666780, 0.000000)))
comp.append(Part.LineSegment(App.Vector(-0.533400, 0.666780, 0.000000), App.Vector(-0.533400, 0.660430, 0.000000)))
comp.append(Part.LineSegment(App.Vector(-0.533400, 0.660430, 0.000000), App.Vector(-0.546100, 0.660430, 0.000000)))
comp.append(Part.LineSegment(App.Vector(-0.666750, 0.660430, 0.000000), App.Vector(-0.666750, 0.666780, 0.000000)))
comp.append(Part.LineSegment(App.Vector(-0.666750, 0.666780, 0.000000), App.Vector(-0.654050, 0.666780, 0.000000)))
comp.append(Part.LineSegment(App.Vector(-0.654050, 0.666780, 0.000000), App.Vector(-0.654050, 0.660430, 0.000000)))
comp.append(Part.LineSegment(App.Vector(-0.654050, 0.660430, 0.000000), App.Vector(-0.666750, 0.660430, 0.000000)))
comp.append(Part.LineSegment(App.Vector(-0.546100, 0.673130, 0.000000), App.Vector(-0.533400, 0.673130, 0.000000)))
comp.append(Part.LineSegment(App.Vector(-0.533400, 0.673130, 0.000000), App.Vector(-0.533400, 0.666780, 0.000000)))
comp.append(Part.LineSegment(App.Vector(-0.533400, 0.666780, 0.000000), App.Vector(-0.546100, 0.666780, 0.000000)))
comp.append(Part.LineSegment(App.Vector(-0.546100, 0.666780, 0.000000), App.Vector(-0.546100, 0.673130, 0.000000)))
comp.append(Part.LineSegment(App.Vector(-0.666750, 0.673130, 0.000000), App.Vector(-0.654050, 0.673130, 0.000000)))
comp.append(Part.LineSegment(App.Vector(-0.654050, 0.673130, 0.000000), App.Vector(-0.654050, 0.666780, 0.000000)))
comp.append(Part.LineSegment(App.Vector(-0.654050, 0.666780, 0.000000), App.Vector(-0.666750, 0.666780, 0.000000)))
comp.append(Part.LineSegment(App.Vector(-0.666750, 0.666780, 0.000000), App.Vector(-0.666750, 0.673130, 0.000000)))
comp.append(Part.LineSegment(App.Vector(-0.145300, 0.082500, 0.000000), App.Vector(-0.145300, 0.002900, 0.000000)))
comp.append(Part.LineSegment(App.Vector(-0.145300, 0.002900, 0.000000), App.Vector(0.145300, 0.002900, 0.000000)))
comp.append(Part.LineSegment(App.Vector(0.145300, 0.002900, 0.000000), App.Vector(0.145300, 0.082500, 0.000000)))
comp.append(Part.LineSegment(App.Vector(0.145300, 0.082500, 0.000000), App.Vector(0.155000, 0.082500, 0.000000)))
comp.append(Part.LineSegment(App.Vector(0.155000, 0.082500, 0.000000), App.Vector(0.155000, -0.082500, 0.000000)))
comp.append(Part.LineSegment(App.Vector(0.155000, -0.082500, 0.000000), App.Vector(0.145300, -0.082500, 0.000000)))
comp.append(Part.LineSegment(App.Vector(0.145300, -0.082500, 0.000000), App.Vector(0.145300, -0.002900, 0.000000)))
comp.append(Part.LineSegment(App.Vector(0.145300, -0.002900, 0.000000), App.Vector(-0.145300, -0.002900, 0.000000)))
comp.append(Part.LineSegment(App.Vector(-0.145300, -0.002900, 0.000000), App.Vector(-0.145300, -0.082500, 0.000000)))
comp.append(Part.LineSegment(App.Vector(-0.145300, -0.082500, 0.000000), App.Vector(-0.155000, -0.082500, 0.000000)))
comp.append(Part.LineSegment(App.Vector(-0.155000, -0.082500, 0.000000), App.Vector(-0.155000, 0.082500, 0.000000)))
comp.append(Part.LineSegment(App.Vector(-0.155000, 0.082500, 0.000000), App.Vector(-0.145300, 0.082500, 0.000000)))
comp.append(Part.LineSegment(App.Vector(-0.145300, 0.082500, 0.000000), App.Vector(-0.145300, 0.020200, 0.000000)))
comp.append(Part.LineSegment(App.Vector(-0.128000, 0.002900, 0.000000), App.Vector(0.128000, 0.002900, 0.000000)))
comp.append(Part.LineSegment(App.Vector(0.145300, 0.020200, 0.000000), App.Vector(0.145300, 0.082500, 0.000000)))
comp.append(Part.LineSegment(App.Vector(0.145300, -0.082500, 0.000000), App.Vector(0.145300, -0.020200, 0.000000)))
comp.append(Part.LineSegment(App.Vector(0.128000, -0.002900, 0.000000), App.Vector(-0.128000, -0.002900, 0.000000)))
comp.append(Part.LineSegment(App.Vector(-0.145300, -0.020200, 0.000000), App.Vector(-0.145300, -0.082500, 0.000000)))
comp.append(Part.LineSegment(App.Vector(-0.152400, 0.000000, 0.000000), App.Vector(0.000000, 0.000000, 0.000000)))
comp.append(Part.LineSegment(App.Vector(0.000000, 0.000000, 0.000000), App.Vector(-0.000000, 0.152400, 0.000000)))
comp.append(Part.LineSegment(App.Vector(-0.000000, 0.152400, 0.000000), App.Vector(-0.152400, 0.152400, 0.000000)))
comp.append(Part.LineSegment(App.Vector(-0.152400, 0.152400, 0.000000), App.Vector(-0.152400, 0.000000, 0.000000)))
comp.append(Part.LineSegment(App.Vector(-0.141500, 0.082500, 0.000000), App.Vector(-0.141500, 0.011900, 0.000000)))
comp.append(Part.LineSegment(App.Vector(-0.132600, 0.003000, 0.000000), App.Vector(0.132600, 0.003000, 0.000000)))
comp.append(Part.LineSegment(App.Vector(0.141500, 0.011900, 0.000000), App.Vector(0.141500, 0.082500, 0.000000)))
comp.append(Part.LineSegment(App.Vector(0.141500, 0.082500, 0.000000), App.Vector(0.151700, 0.082500, 0.000000)))
comp.append(Part.LineSegment(App.Vector(0.151700, 0.082500, 0.000000), App.Vector(0.151700, -0.082500, 0.000000)))
comp.append(Part.LineSegment(App.Vector(0.151700, -0.082500, 0.000000), App.Vector(0.141500, -0.082500, 0.000000)))
comp.append(Part.LineSegment(App.Vector(0.141500, -0.082500, 0.000000), App.Vector(0.141500, -0.011900, 0.000000)))
comp.append(Part.LineSegment(App.Vector(0.132600, -0.003000, 0.000000), App.Vector(-0.132600, -0.003000, 0.000000)))
comp.append(Part.LineSegment(App.Vector(-0.141500, -0.011900, 0.000000), App.Vector(-0.141500, -0.082500, 0.000000)))
comp.append(Part.LineSegment(App.Vector(-0.141500, -0.082500, 0.000000), App.Vector(-0.151700, -0.082500, 0.000000)))
comp.append(Part.LineSegment(App.Vector(-0.151700, -0.082500, 0.000000), App.Vector(-0.151700, 0.082500, 0.000000)))
comp.append(Part.LineSegment(App.Vector(-0.151700, 0.082500, 0.000000), App.Vector(-0.141500, 0.082500, 0.000000)))
comp.append(Part.LineSegment(App.Vector(-0.141500, 0.082500, 0.000000), App.Vector(-0.141500, 0.003000, 0.000000)))
comp.append(Part.LineSegment(App.Vector(-0.141500, 0.003000, 0.000000), App.Vector(0.141500, 0.003000, 0.000000)))
comp.append(Part.LineSegment(App.Vector(0.141500, 0.003000, 0.000000), App.Vector(0.141500, 0.082500, 0.000000)))
comp.append(Part.LineSegment(App.Vector(0.141500, -0.082500, 0.000000), App.Vector(0.141500, -0.003000, 0.000000)))
comp.append(Part.LineSegment(App.Vector(0.141500, -0.003000, 0.000000), App.Vector(-0.141500, -0.003000, 0.000000)))
comp.append(Part.LineSegment(App.Vector(-0.141500, -0.003000, 0.000000), App.Vector(-0.141500, -0.082500, 0.000000)))
comp.append(Part.LineSegment(App.Vector(-0.762500, 0.000000, 0.000000), App.Vector(-0.000000, 0.000000, 0.000000)))
comp.append(Part.LineSegment(App.Vector(-0.000000, 0.000000, 0.000000), App.Vector(-0.000000, 0.762500, 0.000000)))
comp.append(Part.LineSegment(App.Vector(-0.000000, 0.762500, 0.000000), App.Vector(-0.762500, 0.762500, 0.000000)))
comp.append(Part.LineSegment(App.Vector(-0.762500, 0.762500, 0.000000), App.Vector(-0.762500, 0.000000, 0.000000)))
comp.append(Part.LineSegment(App.Vector(-0.737100, 0.025400, 0.000000), App.Vector(-0.737100, 0.737100, 0.000000)))
comp.append(Part.LineSegment(App.Vector(-0.737100, 0.737100, 0.000000), App.Vector(-0.025400, 0.737100, 0.000000)))
comp.append(Part.LineSegment(App.Vector(-0.025400, 0.737100, 0.000000), App.Vector(-0.025400, 0.025400, 0.000000)))
comp.append(Part.LineSegment(App.Vector(-0.025400, 0.025400, 0.000000), App.Vector(-0.737100, 0.025400, 0.000000)))
comp.append(Part.LineSegment(App.Vector(-0.660900, 0.000000, 0.000000), App.Vector(-0.660900, 0.050800, 0.000000)))
comp.append(Part.LineSegment(App.Vector(-0.660900, 0.050800, 0.000000), App.Vector(-0.711700, 0.050800, 0.000000)))
comp.append(Part.LineSegment(App.Vector(-0.711700, 0.050800, 0.000000), App.Vector(-0.711700, 0.000000, 0.000000)))
comp.append(Part.LineSegment(App.Vector(-0.711700, 0.000000, 0.000000), App.Vector(-0.660900, 0.000000, 0.000000)))
comp.append(Part.LineSegment(App.Vector(-0.660900, 0.711700, 0.000000), App.Vector(-0.711700, 0.711700, 0.000000)))
comp.append(Part.LineSegment(App.Vector(-0.711700, 0.711700, 0.000000), App.Vector(-0.711700, 0.660900, 0.000000)))
comp.append(Part.LineSegment(App.Vector(-0.711700, 0.660900, 0.000000), App.Vector(-0.660900, 0.660900, 0.000000)))
comp.append(Part.LineSegment(App.Vector(-0.660900, 0.660900, 0.000000), App.Vector(-0.660900, 0.711700, 0.000000)))
comp.append(Part.LineSegment(App.Vector(-0.050800, 0.711700, 0.000000), App.Vector(-0.050800, 0.660900, 0.000000)))
comp.append(Part.LineSegment(App.Vector(-0.050800, 0.660900, 0.000000), App.Vector(-0.000000, 0.660900, 0.000000)))
comp.append(Part.LineSegment(App.Vector(-0.000000, 0.660900, 0.000000), App.Vector(-0.000000, 0.711700, 0.000000)))
comp.append(Part.LineSegment(App.Vector(-0.000000, 0.711700, 0.000000), App.Vector(-0.050800, 0.711700, 0.000000)))
comp.append(Part.LineSegment(App.Vector(0.000000, 0.000000, 0.000000), App.Vector(0.000000, 0.711700, 0.000000)))
comp.append(Part.LineSegment(App.Vector(0.000000, 0.711700, 0.000000), App.Vector(-0.711700, 0.711700, 0.000000)))
comp.append(Part.LineSegment(App.Vector(-0.711700, 0.711700, 0.000000), App.Vector(-0.711700, 0.000000, 0.000000)))
comp.append(Part.LineSegment(App.Vector(-0.660900, 0.050800, 0.000000), App.Vector(-0.660900, 0.660900, 0.000000)))
comp.append(Part.LineSegment(App.Vector(-0.660900, 0.660900, 0.000000), App.Vector(-0.050800, 0.660900, 0.000000)))
comp.append(Part.LineSegment(App.Vector(-0.050800, 0.660900, 0.000000), App.Vector(-0.050800, 0.050800, 0.000000)))
comp.append(Part.LineSegment(App.Vector(-0.050800, 0.050800, 0.000000), App.Vector(-0.660900, 0.050800, 0.000000)))
comp.append(Part.LineSegment(App.Vector(-0.000000, -0.000000, 0.000000), App.Vector(2.089912, -0.000000, 0.000000)))
comp.append(Part.LineSegment(App.Vector(-0.000000, -0.000000, 0.000000), App.Vector(2.205247, -0.000000, 0.000000)))
obj = doc.addObject("Part::Feature", "NIVEL_+0.000")
obj.Label = "NIVEL_+0.000"
obj.Shape = Part.Shape(comp)
grp.addObject(obj)

grp = doc.addObject("App::DocumentObjectGroup", "NIVEL_+4.370")
grp.Label = "NIVEL_+4.370 (linhas de localizacao)"
comp = []
comp.append(Part.LineSegment(App.Vector(48.880202, 34.266199, 4.370000), App.Vector(48.880202, 36.906199, 4.370000)))
comp.append(Part.LineSegment(App.Vector(53.670202, 34.266199, 4.370000), App.Vector(48.880202, 34.266199, 4.370000)))
comp.append(Part.LineSegment(App.Vector(0.000000, 10.951500, 4.370000), App.Vector(4.790000, 10.951500, 4.370000)))
comp.append(Part.LineSegment(App.Vector(4.790000, 10.951500, 4.370000), App.Vector(4.790000, 8.311500, 4.370000)))
comp.append(Part.LineSegment(App.Vector(4.790000, 8.311500, 4.370000), App.Vector(0.000000, 8.311500, 4.370000)))
comp.append(Part.LineSegment(App.Vector(0.000000, 66.066878, 4.370000), App.Vector(4.790000, 66.066878, 4.370000)))
comp.append(Part.LineSegment(App.Vector(4.790000, 66.066878, 4.370000), App.Vector(4.790000, 63.426878, 4.370000)))
comp.append(Part.LineSegment(App.Vector(4.790000, 63.426878, 4.370000), App.Vector(0.000000, 63.426878, 4.370000)))
comp.append(Part.LineSegment(App.Vector(8.111500, 20.574850, 4.370000), App.Vector(8.111500, 18.711051, 4.370000)))
comp.append(Part.LineSegment(App.Vector(8.111500, 18.711051, 4.370000), App.Vector(5.935000, 18.711051, 4.370000)))
comp.append(Part.LineSegment(App.Vector(5.935000, 18.711051, 4.370000), App.Vector(5.935000, 20.574850, 4.370000)))
comp.append(Part.LineSegment(App.Vector(5.935000, 20.574850, 4.370000), App.Vector(8.111500, 20.574850, 4.370000)))
comp.append(Part.LineSegment(App.Vector(10.909301, 13.727920, 4.370000), App.Vector(18.834101, 13.727920, 4.370000)))
comp.append(Part.LineSegment(App.Vector(18.834101, 13.727920, 4.370000), App.Vector(18.834101, 10.907720, 4.370000)))
comp.append(Part.LineSegment(App.Vector(18.834101, 10.907720, 4.370000), App.Vector(10.909301, 10.907720, 4.370000)))
comp.append(Part.LineSegment(App.Vector(10.909301, 10.907720, 4.370000), App.Vector(10.909301, 13.727920, 4.370000)))
comp.append(Part.LineSegment(App.Vector(21.882101, 13.727920, 4.370000), App.Vector(29.806901, 13.727920, 4.370000)))
comp.append(Part.LineSegment(App.Vector(29.806901, 13.727920, 4.370000), App.Vector(29.806901, 10.907720, 4.370000)))
comp.append(Part.LineSegment(App.Vector(29.806901, 10.907720, 4.370000), App.Vector(21.882101, 10.907720, 4.370000)))
comp.append(Part.LineSegment(App.Vector(21.882101, 10.907720, 4.370000), App.Vector(21.882101, 13.727920, 4.370000)))
comp.append(Part.LineSegment(App.Vector(32.854901, 13.717920, 4.370000), App.Vector(40.779701, 13.717920, 4.370000)))
comp.append(Part.LineSegment(App.Vector(40.779701, 13.717920, 4.370000), App.Vector(40.779701, 10.927920, 4.370000)))
comp.append(Part.LineSegment(App.Vector(40.779701, 10.927920, 4.370000), App.Vector(32.854901, 10.927920, 4.370000)))
comp.append(Part.LineSegment(App.Vector(32.854901, 10.927920, 4.370000), App.Vector(32.854901, 13.717920, 4.370000)))
obj = doc.addObject("Part::Feature", "NIVEL_+4.370")
obj.Label = "NIVEL_+4.370"
obj.Shape = Part.Shape(comp)
grp.addObject(obj)

grp = doc.addObject("App::DocumentObjectGroup", "NIVEL_+8.170")
grp.Label = "NIVEL_+8.170 (linhas de localizacao)"
comp = []
comp.append(Part.LineSegment(App.Vector(48.880202, 34.266199, 8.170000), App.Vector(48.880202, 36.906199, 8.170000)))
comp.append(Part.LineSegment(App.Vector(53.670202, 34.266199, 8.170000), App.Vector(48.880202, 34.266199, 8.170000)))
comp.append(Part.LineSegment(App.Vector(0.000000, 10.951500, 8.170000), App.Vector(4.790000, 10.951500, 8.170000)))
comp.append(Part.LineSegment(App.Vector(4.790000, 10.951500, 8.170000), App.Vector(4.790000, 8.311500, 8.170000)))
comp.append(Part.LineSegment(App.Vector(4.790000, 8.311500, 8.170000), App.Vector(0.000000, 8.311500, 8.170000)))
comp.append(Part.LineSegment(App.Vector(0.000000, 66.066878, 8.170000), App.Vector(4.790000, 66.066878, 8.170000)))
comp.append(Part.LineSegment(App.Vector(4.790000, 66.066878, 8.170000), App.Vector(4.790000, 63.426878, 8.170000)))
comp.append(Part.LineSegment(App.Vector(4.790000, 63.426878, 8.170000), App.Vector(0.000000, 63.426878, 8.170000)))
comp.append(Part.LineSegment(App.Vector(8.111500, 20.574850, 8.170000), App.Vector(8.111500, 18.711051, 8.170000)))
comp.append(Part.LineSegment(App.Vector(8.111500, 18.711051, 8.170000), App.Vector(5.935000, 18.711051, 8.170000)))
comp.append(Part.LineSegment(App.Vector(5.935000, 18.711051, 8.170000), App.Vector(5.935000, 20.574850, 8.170000)))
comp.append(Part.LineSegment(App.Vector(5.935000, 20.574850, 8.170000), App.Vector(8.111500, 20.574850, 8.170000)))
comp.append(Part.LineSegment(App.Vector(10.909301, 13.727920, 8.170000), App.Vector(18.834101, 13.727920, 8.170000)))
comp.append(Part.LineSegment(App.Vector(18.834101, 13.727920, 8.170000), App.Vector(18.834101, 10.907720, 8.170000)))
comp.append(Part.LineSegment(App.Vector(18.834101, 10.907720, 8.170000), App.Vector(10.909301, 10.907720, 8.170000)))
comp.append(Part.LineSegment(App.Vector(10.909301, 10.907720, 8.170000), App.Vector(10.909301, 13.727920, 8.170000)))
comp.append(Part.LineSegment(App.Vector(21.882101, 13.727920, 8.170000), App.Vector(29.806901, 13.727920, 8.170000)))
comp.append(Part.LineSegment(App.Vector(29.806901, 13.727920, 8.170000), App.Vector(29.806901, 10.907720, 8.170000)))
comp.append(Part.LineSegment(App.Vector(29.806901, 10.907720, 8.170000), App.Vector(21.882101, 10.907720, 8.170000)))
comp.append(Part.LineSegment(App.Vector(21.882101, 10.907720, 8.170000), App.Vector(21.882101, 13.727920, 8.170000)))
comp.append(Part.LineSegment(App.Vector(32.854901, 13.717920, 8.170000), App.Vector(40.779701, 13.717920, 8.170000)))
comp.append(Part.LineSegment(App.Vector(40.779701, 13.717920, 8.170000), App.Vector(40.779701, 10.927920, 8.170000)))
comp.append(Part.LineSegment(App.Vector(40.779701, 10.927920, 8.170000), App.Vector(32.854901, 10.927920, 8.170000)))
comp.append(Part.LineSegment(App.Vector(32.854901, 10.927920, 8.170000), App.Vector(32.854901, 13.717920, 8.170000)))
obj = doc.addObject("Part::Feature", "NIVEL_+8.170")
obj.Label = "NIVEL_+8.170"
obj.Shape = Part.Shape(comp)
grp.addObject(obj)

sheet = doc.addObject("Spreadsheet::Sheet", "Elementos")
sheet.set("A1", "id"); sheet.set("B1", "nome")
sheet.set("A2", "86291"); sheet.set("B2", "Standard")
sheet.set("A3", "274965"); sheet.set("B3", "A10")
sheet.set("A4", "397"); sheet.set("B4", "Exterior - Brick on Mtl. Stud")
sheet.set("A5", "398"); sheet.set("B5", "Generic - 200mm")
sheet.set("A6", "399"); sheet.set("B6", "Generic - 225mm Masonry")
sheet.set("A7", "400"); sheet.set("B7", "Generic - 140mm Masonry")
sheet.set("A8", "401"); sheet.set("B8", "Generic - 90mm Brick")
sheet.set("A9", "402"); sheet.set("B9", "Interior - 79mm Partition (1-hr)")
sheet.set("A10", "403"); sheet.set("B10", "Interior - Blockwork 100")
sheet.set("A11", "404"); sheet.set("B11", "Interior - 135mm Partition (2-hr)")
sheet.set("A12", "408"); sheet.set("B12", "CW 102-50-100p")
sheet.set("A13", "410"); sheet.set("B13", "CW 102-85-140p")
sheet.set("A14", "411"); sheet.set("B14", "CW 102-50-140p")
sheet.set("A15", "412"); sheet.set("B15", "CW 102-50-215p")
sheet.set("A16", "413"); sheet.set("B16", "CW 102-85-215p")
sheet.set("A17", "1049"); sheet.set("B17", "M_Section Head - Filled")
sheet.set("A18", "1141"); sheet.set("B18", "Metric Callout")
sheet.set("A19", "1233"); sheet.set("B19", "M_Door Tag")
sheet.set("A20", "3378"); sheet.set("B20", "BS Universal Beam")
sheet.set("A21", "3393"); sheet.set("B21", "Centre F/B")
sheet.set("A22", "3395"); sheet.set("B22", "Centre L/R")
sheet.set("A23", "3441"); sheet.set("B23", "Arial")
sheet.set("A24", "3532"); sheet.set("B24", "Steel")
sheet.set("A25", "3546"); sheet.set("B25", "203x133x30UB")
sheet.set("A26", "3547"); sheet.set("B26", "254x146x31UB")
sheet.set("A27", "3548"); sheet.set("B27", "305x127x37UB")
sheet.set("A28", "3549"); sheet.set("B28", "356x171x45UB")
sheet.set("A29", "3550"); sheet.set("B29", "406x178x54UB")
sheet.set("A30", "3551"); sheet.set("B30", "305x165x40UB")
sheet.set("A31", "3552"); sheet.set("B31", "457x152x52UB")
sheet.set("A32", "3553"); sheet.set("B32", "457x191x67UB")
sheet.set("A33", "3554"); sheet.set("B33", "533x210x82UB")
sheet.set("A34", "3555"); sheet.set("B34", "610x229x101UB")
sheet.set("A35", "3556"); sheet.set("B35", "686x254x125UB")
sheet.set("A36", "3557"); sheet.set("B36", "254x102x22UB")
sheet.set("A37", "3558"); sheet.set("B37", "305x102x25UB")
sheet.set("A38", "3796"); sheet.set("B38", "M_Window Tag")
sheet.set("A39", "4169"); sheet.set("B39", "M_View Title")
sheet.set("A40", "5476"); sheet.set("B40", "CW 102-85-100p")
sheet.set("A41", "5533"); sheet.set("B41", "Interior - Blockwork 140")
sheet.set("A42", "5541"); sheet.set("B42", "Interior - Blockwork 190")
sheet.set("A43", "6291"); sheet.set("B43", "Generic - 300mm")
sheet.set("A44", "8486"); sheet.set("B44", "50 x 150mm")
sheet.set("A45", "8488"); sheet.set("B45", "50mm Radius")
sheet.set("A46", "8490"); sheet.set("B46", "30mm Square")
sheet.set("A47", "8492"); sheet.set("B47", "25mm Radius")
sheet.set("A48", "8678"); sheet.set("B48", "M_North Arrow-2")
sheet.set("A49", "8785"); sheet.set("B49", "M_Area Tag")
sheet.set("A50", "9426"); sheet.set("B50", "Foundation - 300mm Concrete")
sheet.set("A51", "9427"); sheet.set("B51", "Retaining - 300mm Concrete")
sheet.set("A52", "12611"); sheet.set("B52", "Glazed")
sheet.set("A53", "12615"); sheet.set("B53", "Empty")
sheet.set("A54", "12963"); sheet.set("B54", "4800 x 2400mm - 90 deg")
sheet.set("A55", "12965"); sheet.set("B55", "4800 x 2400mm - 60 deg")
sheet.set("A56", "12967"); sheet.set("B56", "4800 x 2400mm - 80 deg")
sheet.set("A57", "12969"); sheet.set("B57", "4800 x 2400mm - 70 deg")
sheet.set("A58", "16216"); sheet.set("B58", "50 x 50mm")
sheet.set("A59", "16332"); sheet.set("B59", "30mm")
sheet.set("A60", "16334"); sheet.set("B60", "40mm")
sheet.set("A61", "16334"); sheet.set("B61", "ä(")
sheet.set("A62", "29086"); sheet.set("B62", "M_Section Head - Open")
sheet.set("A63", "29292"); sheet.set("B63", "Running Section")
sheet.set("A64", "33067"); sheet.set("B64", "10")
sheet.set("A65", "33069"); sheet.set("B65", "11")
sheet.set("A66", "33071"); sheet.set("B66", "12")
sheet.set("A67", "33073"); sheet.set("B67", "13")
sheet.set("A68", "33075"); sheet.set("B68", "14")
sheet.set("A69", "33077"); sheet.set("B69", "15")
sheet.set("A70", "33079"); sheet.set("B70", "16")
sheet.set("A71", "33081"); sheet.set("B71", "17")
sheet.set("A72", "33083"); sheet.set("B72", "18")
sheet.set("A73", "35764"); sheet.set("B73", "Solid")
sheet.set("A74", "36223"); sheet.set("B74", "12mm")
sheet.set("A75", "36225"); sheet.set("B75", "8mm")
sheet.set("A76", "38520"); sheet.set("B76", "20mm")
sheet.set("A77", "38522"); sheet.set("B77", "30mm")
sheet.set("A78", "38524"); sheet.set("B78", "40mm")
sheet.set("A79", "42082"); sheet.set("B79", "Soldier & Plan")
sheet.set("A80", "42084"); sheet.set("B80", "Rowlock")
sheet.set("A81", "49480"); sheet.set("B81", "20")
sheet.set("A82", "49482"); sheet.set("B82", "22")
sheet.set("A83", "49484"); sheet.set("B83", "24")
sheet.set("A84", "49486"); sheet.set("B84", "26")
sheet.set("A85", "49488"); sheet.set("B85", "28")
sheet.set("A86", "49490"); sheet.set("B86", "30")
sheet.set("A87", "49492"); sheet.set("B87", "32")
sheet.set("A88", "52557"); sheet.set("B88", "ÿ$")
sheet.set("A89", "52559"); sheet.set("B89", "ÿ$")
sheet.set("A90", "52561"); sheet.set("B90", "ÿ$")
sheet.set("A91", "54538"); sheet.set("B91", "Exterior - Block on Mtl. Stud")
sheet.set("A92", "54539"); sheet.set("B92", "Wall")
sheet.set("A93", "55347"); sheet.set("B93", "Room Tag")
sheet.set("A94", "55349"); sheet.set("B94", "Room Tag With Area")
sheet.set("A95", "86544"); sheet.set("B95", "Keynote Number - Boxed")
sheet.set("A96", "86546"); sheet.set("B96", "Keynote Number")
sheet.set("A97", "86548"); sheet.set("B97", "Keynote Text")
sheet.set("A98", "86745"); sheet.set("B98", "M_Material Tag")
sheet.set("A99", "86959"); sheet.set("B99", "Room Tag With Volume")
sheet.set("A100", "100162"); sheet.set("B100", "M_View Reference")
sheet.set("A101", "100394"); sheet.set("B101", "M_Spot Elevation - Crosshair")
sheet.set("A102", "102346"); sheet.set("B102", "M_Revision Tag")
sheet.set("A103", "105461"); sheet.set("B103", "Scarlet Oak - 12.5 Meters")
sheet.set("A104", "105463"); sheet.set("B104", "Red Maple - 9 Meters")
sheet.set("A105", "105465"); sheet.set("B105", "Kousa Dogwood - 3.0 Meters")
sheet.set("A106", "105467"); sheet.set("B106", "Lombardy Poplar - 12.2 Meters")
sheet.set("A107", "105469"); sheet.set("B107", "Siberian Crab Apple - 6.1 Meters")
sheet.set("A108", "105471"); sheet.set("B108", "Gray Birch - 3.1 Meters")
sheet.set("A109", "105473"); sheet.set("B109", "Red Ash - 7.6 Meters")
sheet.set("A110", "105475"); sheet.set("B110", "Fraxinus - 5.6 Meters")
sheet.set("A111", "105477"); sheet.set("B111", "American Beech - 6.0 Meters")
sheet.set("A112", "105479"); sheet.set("B112", "Blue Berry Elder - 4.5 Meters")
sheet.set("A113", "105481"); sheet.set("B113", "Comman Apple - 6.0 Meters")
sheet.set("A114", "105483"); sheet.set("B114", "Golden Chain - 5.5 Meters")
sheet.set("A115", "105485"); sheet.set("B115", "Hawthorn - 7.4 Meters")
sheet.set("A116", "105487"); sheet.set("B116", "Honey Locust - 7.6 Meters")
sheet.set("A117", "105489"); sheet.set("B117", "Japanese Cherry - 4.5 Meters")
sheet.set("A118", "105491"); sheet.set("B118", "Japanese Maple - 3.0 Meters")
sheet.set("A119", "105493"); sheet.set("B119", "Largetooth Aspen - 7.6 Meters")
sheet.set("A120", "105495"); sheet.set("B120", "Shumard Oak - 9.1 Meters")
sheet.set("A121", "111916"); sheet.set("B121", "Degrees Minutes Seconds")
sheet.set("A122", "111918"); sheet.set("B122", "Decimal Degrees")
sheet.set("A123", "111933"); sheet.set("B123", "MN")
sheet.set("A124", "130737"); sheet.set("B124", "ÿd")
sheet.set("A125", "131998"); sheet.set("B125", "ÿ#")
sheet.set("A126", "135164"); sheet.set("B126", "ÿK")
sheet.set("A127", "135166"); sheet.set("B127", "ÿK")
sheet.set("A128", "135168"); sheet.set("B128", "ÿK")
sheet.set("A129", "135170"); sheet.set("B129", "ÿK")
sheet.set("A130", "135172"); sheet.set("B130", "ÿK")
sheet.set("A131", "135174"); sheet.set("B131", "ÿK")
sheet.set("A132", "135176"); sheet.set("B132", "ÿK")
sheet.set("A133", "135178"); sheet.set("B133", "ÿK")
sheet.set("A134", "135180"); sheet.set("B134", "ÿK")
sheet.set("A135", "135182"); sheet.set("B135", "ÿK")
sheet.set("A136", "135184"); sheet.set("B136", "ÿK")
sheet.set("A137", "135186"); sheet.set("B137", "ÿK")
sheet.set("A138", "135188"); sheet.set("B138", "ÿK")
sheet.set("A139", "135190"); sheet.set("B139", "ÿK")
sheet.set("A140", "135194"); sheet.set("B140", "ÿK")
sheet.set("A141", "135196"); sheet.set("B141", "ÿK")
sheet.set("A142", "135198"); sheet.set("B142", "ÿK")
sheet.set("A143", "135200"); sheet.set("B143", "ÿK")
sheet.set("A144", "135202"); sheet.set("B144", "ÿK")
sheet.set("A145", "135204"); sheet.set("B145", "ÿK")
sheet.set("A146", "135206"); sheet.set("B146", "ÿK")
sheet.set("A147", "135208"); sheet.set("B147", "ÿK")
sheet.set("A148", "135210"); sheet.set("B148", "ÿK")
sheet.set("A149", "135212"); sheet.set("B149", "E@")
sheet.set("A150", "135214"); sheet.set("B150", "ÿK")
sheet.set("A151", "135216"); sheet.set("B151", "ÿK")
sheet.set("A152", "135218"); sheet.set("B152", "ÿK")
sheet.set("A153", "135220"); sheet.set("B153", "ÿK")
sheet.set("A154", "135222"); sheet.set("B154", "ÿK")
sheet.set("A155", "135224"); sheet.set("B155", "ÿK")
sheet.set("A156", "135226"); sheet.set("B156", "ÿK")
sheet.set("A157", "135228"); sheet.set("B157", "ÿK")
sheet.set("A158", "135230"); sheet.set("B158", "ÿK")
sheet.set("A159", "135232"); sheet.set("B159", "ÿK")
sheet.set("A160", "135408"); sheet.set("B160", "Landscape Schedule")
sheet.set("A161", "139448"); sheet.set("B161", "1.1")
sheet.set("A162", "139678"); sheet.set("B162", "Main Building")
sheet.set("A163", "139682"); sheet.set("B163", "ÿ\"")
sheet.set("A164", "139737"); sheet.set("B164", "ÿ,")
sheet.set("A165", "139739"); sheet.set("B165", "ÿG")
sheet.set("A166", "139752"); sheet.set("B166", "Mass Floor Schedule")
sheet.set("A167", "139759"); sheet.set("B167", "Pavillion")
sheet.set("A168", "139785"); sheet.set("B168", "Pavillion")
sheet.set("A169", "139787"); sheet.set("B169", "ÿ'")
sheet.set("A170", "140015"); sheet.set("B170", "ÿý")
sheet.set("A171", "140081"); sheet.set("B171", "Building Courtyard")
sheet.set("A172", "140902"); sheet.set("B172", "300mm")
sheet.set("A173", "140904"); sheet.set("B173", "450mm")
sheet.set("A174", "140906"); sheet.set("B174", "600mm")
sheet.set("A175", "140908"); sheet.set("B175", "750mm")
sheet.set("A176", "142430"); sheet.set("B176", "ÿ$")
sheet.set("A177", "144180"); sheet.set("B177", "ÿÒ")
sheet.set("A178", "144230"); sheet.set("B178", "ÿZ")
sheet.set("A179", "144289"); sheet.set("B179", "ÿM")
sheet.set("A180", "145054"); sheet.set("B180", "ÿE")
sheet.set("A181", "145211"); sheet.set("B181", "ÿL")
sheet.set("A182", "145263"); sheet.set("B182", "ÿC")
sheet.set("A183", "145547"); sheet.set("B183", "ÿÐ")
sheet.set("A184", "145891"); sheet.set("B184", "10")
sheet.set("A185", "145999"); sheet.set("B185", "122")
sheet.set("A186", "146094"); sheet.set("B186", "124")
sheet.set("A187", "146152"); sheet.set("B187", "125")
sheet.set("A188", "146282"); sheet.set("B188", "123")
sheet.set("A189", "146343"); sheet.set("B189", "126")
sheet.set("A190", "146483"); sheet.set("B190", "129")
sheet.set("A191", "146563"); sheet.set("B191", "128")
sheet.set("A192", "146641"); sheet.set("B192", "127")
sheet.set("A193", "146741"); sheet.set("B193", "130")
sheet.set("A194", "147401"); sheet.set("B194", "33")
sheet.set("A195", "147403"); sheet.set("B195", "34")
sheet.set("A196", "147405"); sheet.set("B196", "35")
sheet.set("A197", "147407"); sheet.set("B197", "36")
sheet.set("A198", "147409"); sheet.set("B198", "37")
sheet.set("A199", "147834"); sheet.set("B199", "130A")
sheet.set("A200", "0"); sheet.set("B200", "Yè")
sheet.set("A201", "0"); sheet.set("B201", "Yè")
sheet.set("A202", "0"); sheet.set("B202", "\"ì")
sheet.set("A203", "0"); sheet.set("B203", "åL")
sheet.set("A204", "0"); sheet.set("B204", "åL")
sheet.set("A205", "0"); sheet.set("B205", "åL")
sheet.set("A206", "0"); sheet.set("B206", "åL")
sheet.set("A207", "149189"); sheet.set("B207", "ÿe")
sheet.set("A208", "149293"); sheet.set("B208", "ÿK")
sheet.set("A209", "149395"); sheet.set("B209", "ÿK")
sheet.set("A210", "149589"); sheet.set("B210", "ÿM")
sheet.set("A211", "149921"); sheet.set("B211", "119A")
sheet.set("A212", "150034"); sheet.set("B212", "119B")
sheet.set("A213", "150153"); sheet.set("B213", "118")
sheet.set("A214", "150403"); sheet.set("B214", "117")
sheet.set("A215", "150461"); sheet.set("B215", "116")
sheet.set("A216", "150584"); sheet.set("B216", "115")
sheet.set("A217", "150861"); sheet.set("B217", "ÿy")
sheet.set("A218", "151331"); sheet.set("B218", "ÿv")
sheet.set("A219", "151588"); sheet.set("B219", "ÿe")
sheet.set("A220", "151594"); sheet.set("B220", "114")
sheet.set("A221", "152037"); sheet.set("B221", "ÿE")
sheet.set("A222", "152111"); sheet.set("B222", "ÿV")
sheet.set("A223", "152271"); sheet.set("B223", "ÿY")
sheet.set("A224", "152378"); sheet.set("B224", "111")
sheet.set("A225", "152476"); sheet.set("B225", "112")
sheet.set("A226", "152622"); sheet.set("B226", "110")
sheet.set("A227", "152688"); sheet.set("B227", "109")
sheet.set("A228", "152882"); sheet.set("B228", "ÿC")
sheet.set("A229", "153000"); sheet.set("B229", "ÿE")
sheet.set("A230", "153162"); sheet.set("B230", "ÿ;")
sheet.set("A231", "153242"); sheet.set("B231", "ÿ;")
sheet.set("A232", "153435"); sheet.set("B232", "ÿÚ")
sheet.set("A233", "156408"); sheet.set("B233", "ÿû")
sheet.set("A234", "156685"); sheet.set("B234", "ËÀ")
sheet.set("A235", "156686"); sheet.set("B235", "ÿ$")
sheet.set("A236", "156744"); sheet.set("B236", "ËÀ")
sheet.set("A237", "156935"); sheet.set("B237", "ÿB")
sheet.set("A238", "157351"); sheet.set("B238", "Level Head - Circle")
sheet.set("A239", "157484"); sheet.set("B239", "ÿ2")
sheet.set("A240", "157644"); sheet.set("B240", "ÿJ")
sheet.set("A241", "157648"); sheet.set("B241", "232")
sheet.set("A242", "157651"); sheet.set("B242", "233")
sheet.set("A243", "14223"); sheet.set("B243", "Ü:")
sheet.set("A244", "50529024"); sheet.set("B244", "Ü:")
sheet.set("A245", "50529024"); sheet.set("B245", "Ü:")
sheet.set("A246", "157705"); sheet.set("B246", "ÿã")
sheet.set("A247", "157717"); sheet.set("B247", "201")
sheet.set("A248", "157780"); sheet.set("B248", "ÿw")
sheet.set("A249", "157781"); sheet.set("B249", "ÿc")
sheet.set("A250", "157782"); sheet.set("B250", "ÿJ")
sheet.set("A251", "157786"); sheet.set("B251", "326")
sheet.set("A252", "157789"); sheet.set("B252", "327")
sheet.set("A253", "157811"); sheet.set("B253", "ÿs")
sheet.set("A254", "157814"); sheet.set("B254", "312")
sheet.set("A255", "157830"); sheet.set("B255", "ÿW")
sheet.set("A256", "157831"); sheet.set("B256", "ÿh")
sheet.set("A257", "157832"); sheet.set("B257", "ÿo")
sheet.set("A258", "157834"); sheet.set("B258", "309")
sheet.set("A259", "157835"); sheet.set("B259", "310")
sheet.set("A260", "157837"); sheet.set("B260", "308")
sheet.set("A261", "157838"); sheet.set("B261", "307")
sheet.set("A262", "157839"); sheet.set("B262", "ÿM")
sheet.set("A263", "157840"); sheet.set("B263", "ÿP")
sheet.set("A264", "157841"); sheet.set("B264", "ÿF")
sheet.set("A265", "157842"); sheet.set("B265", "ÿF")
sheet.set("A266", "157843"); sheet.set("B266", "ÿã")
sheet.set("A267", "159438"); sheet.set("B267", "218")
sheet.set("A268", "159504"); sheet.set("B268", "219A")
sheet.set("A269", "159600"); sheet.set("B269", "219B")
sheet.set("A270", "159676"); sheet.set("B270", "220")
sheet.set("A271", "159736"); sheet.set("B271", "221")
sheet.set("A272", "159804"); sheet.set("B272", "222")
sheet.set("A273", "160661"); sheet.set("B273", "ÿÁ")
sheet.set("A274", "161079"); sheet.set("B274", "231")
sheet.set("A275", "161264"); sheet.set("B275", "230")
sheet.set("A276", "161334"); sheet.set("B276", "229")
sheet.set("A277", "161440"); sheet.set("B277", "226")
sheet.set("A278", "161540"); sheet.set("B278", "228")
sheet.set("A279", "161618"); sheet.set("B279", "225")
sheet.set("A280", "161727"); sheet.set("B280", "227")
sheet.set("A281", "162024"); sheet.set("B281", "234")
sheet.set("A282", "163587"); sheet.set("B282", "306")
sheet.set("A283", "163637"); sheet.set("B283", "305B")
sheet.set("A284", "163705"); sheet.set("B284", "305A")
sheet.set("A285", "163751"); sheet.set("B285", "304B")
sheet.set("A286", "163791"); sheet.set("B286", "304A")
sheet.set("A287", "163825"); sheet.set("B287", "303B")
sheet.set("A288", "163867"); sheet.set("B288", "303A")
sheet.set("A289", "163933"); sheet.set("B289", "302B")
sheet.set("A290", "163995"); sheet.set("B290", "302A")
sheet.set("A291", "164426"); sheet.set("B291", "320B")
sheet.set("A292", "164566"); sheet.set("B292", "320A")
sheet.set("A293", "164626"); sheet.set("B293", "319")
sheet.set("A294", "164674"); sheet.set("B294", "317")
sheet.set("A295", "164768"); sheet.set("B295", "315")
sheet.set("A296", "164869"); sheet.set("B296", "314")
sheet.set("A297", "164921"); sheet.set("B297", "313A")
sheet.set("A298", "164962"); sheet.set("B298", "313B")
sheet.set("A299", "165090"); sheet.set("B299", "316")
sheet.set("A300", "165196"); sheet.set("B300", "ä8")
sheet.set("A301", "165237"); sheet.set("B301", "ÿÔ")
sheet.set("A302", "165368"); sheet.set("B302", "321")
sheet.set("A303", "165462"); sheet.set("B303", "323")
sheet.set("A304", "165525"); sheet.set("B304", "322")
sheet.set("A305", "165571"); sheet.set("B305", "324")
sheet.set("A306", "165645"); sheet.set("B306", "325")
sheet.set("A307", "165700"); sheet.set("B307", "ÿÄ")
sheet.set("A308", "165716"); sheet.set("B308", "ÿê")
sheet.set("A309", "165731"); sheet.set("B309", "ÿÔ")
sheet.set("A310", "165755"); sheet.set("B310", "ÿo")
sheet.set("A311", "167036"); sheet.set("B311", "ÿm")
sheet.set("A312", "167158"); sheet.set("B312", "ÿm")
sheet.set("A313", "167206"); sheet.set("B313", "ÿÕ")
sheet.set("A314", "168547"); sheet.set("B314", "6ä")
sheet.set("A315", "168641"); sheet.set("B315", "GÀ")
sheet.set("A316", "168806"); sheet.set("B316", "ÿD")
sheet.set("A317", "168832"); sheet.set("B317", "ÿ$")
sheet.set("A318", "168854"); sheet.set("B318", "ÿ$")
sheet.set("A319", "169012"); sheet.set("B319", "ÿ$")
sheet.set("A320", "169026"); sheet.set("B320", "ÿ$")
sheet.set("A321", "169082"); sheet.set("B321", " `")
sheet.set("A322", "169082"); sheet.set("B322", " `")
sheet.set("A323", "169082"); sheet.set("B323", " `")
sheet.set("A324", "169082"); sheet.set("B324", " `")
sheet.set("A325", "169082"); sheet.set("B325", " `")
sheet.set("A326", "169402"); sheet.set("B326", "ÿi")
sheet.set("A327", "169602"); sheet.set("B327", "ÿi")
sheet.set("A328", "171298"); sheet.set("B328", "1 1/2\" ")
sheet.set("A329", "171299"); sheet.set("B329", "1\"")
sheet.set("A330", "171300"); sheet.set("B330", "Stair Nosing - Pan")
sheet.set("A331", "172987"); sheet.set("B331", "DN")
sheet.set("A332", "173289"); sheet.set("B332", "MO")
sheet.set("A333", "173290"); sheet.set("B333", "DN")
sheet.set("A334", "173712"); sheet.set("B334", "ÿ1")
sheet.set("A335", "173714"); sheet.set("B335", "ÿ1")
sheet.set("A336", "173716"); sheet.set("B336", "ÿ1")
sheet.set("A337", "174324"); sheet.set("B337", "ÿk")
sheet.set("A338", "174949"); sheet.set("B338", "ÿ8")
sheet.set("A339", "175439"); sheet.set("B339", "ÿK")
sheet.set("A340", "175442"); sheet.set("B340", "ÿk")
sheet.set("A341", "175444"); sheet.set("B341", "ÿK")
sheet.set("A342", "175446"); sheet.set("B342", "ÿ8")
sheet.set("A343", "175522"); sheet.set("B343", "ÿA")
sheet.set("A344", "175634"); sheet.set("B344", "ÿK")
sheet.set("A345", "176407"); sheet.set("B345", "2\" x 2\"")
sheet.set("A346", "176887"); sheet.set("B346", "ÿ1")
sheet.set("A347", "176890"); sheet.set("B347", "ÿ1")
sheet.set("A348", "176908"); sheet.set("B348", "ø@")
sheet.set("A349", "177012"); sheet.set("B349", "ø@")
sheet.set("A350", "177014"); sheet.set("B350", "Balcony View")
sheet.set("A351", "177056"); sheet.set("B351", "101")
sheet.set("A352", "177310"); sheet.set("B352", "127")
sheet.set("A353", "177311"); sheet.set("B353", "126")
sheet.set("A354", "177312"); sheet.set("B354", "128")
sheet.set("A355", "177313"); sheet.set("B355", "129")
sheet.set("A356", "177314"); sheet.set("B356", "130")
sheet.set("A357", "177315"); sheet.set("B357", "131")
sheet.set("A358", "177316"); sheet.set("B358", "119")
sheet.set("A359", "177317"); sheet.set("B359", "118")
sheet.set("A360", "177318"); sheet.set("B360", "117")
sheet.set("A361", "177319"); sheet.set("B361", "120")
sheet.set("A362", "177320"); sheet.set("B362", "116")
sheet.set("A363", "177321"); sheet.set("B363", "115")
sheet.set("A364", "177322"); sheet.set("B364", "114")
sheet.set("A365", "177324"); sheet.set("B365", "112")
sheet.set("A366", "177325"); sheet.set("B366", "111")
sheet.set("A367", "177326"); sheet.set("B367", "110")
sheet.set("A368", "177328"); sheet.set("B368", "109")
sheet.set("A369", "177329"); sheet.set("B369", "107")
sheet.set("A370", "177330"); sheet.set("B370", "108")
sheet.set("A371", "177331"); sheet.set("B371", "106")
sheet.set("A372", "177332"); sheet.set("B372", "105")
sheet.set("A373", "177333"); sheet.set("B373", "104")
sheet.set("A374", "177334"); sheet.set("B374", "103")
sheet.set("A375", "177335"); sheet.set("B375", "132")
sheet.set("A376", "178525"); sheet.set("B376", "02 - Floor")
sheet.set("A377", "178916"); sheet.set("B377", "03 - Floor")
sheet.set("A378", "179125"); sheet.set("B378", "Area Schedule (Gross Building)")
sheet.set("A379", "179173"); sheet.set("B379", "M_Table-Dining Round w Chairs`")
sheet.set("A380", "179679"); sheet.set("B380", "ÿæ")
sheet.set("A381", "180235"); sheet.set("B381", "ÎÀ")
sheet.set("A382", "180745"); sheet.set("B382", "MO")
sheet.set("A383", "180746"); sheet.set("B383", "DN")
sheet.set("A384", "180880"); sheet.set("B384", "ÿA")
sheet.set("A385", "181183"); sheet.set("B385", "MO")
sheet.set("A386", "181184"); sheet.set("B386", "DN")
sheet.set("A387", "181235"); sheet.set("B387", "ÿA")
sheet.set("A388", "181699"); sheet.set("B388", "MK")
sheet.set("A389", "181700"); sheet.set("B389", "DN")
sheet.set("A390", "182100"); sheet.set("B390", "Exterior - Insulation on Masonry")
sheet.set("A391", "182503"); sheet.set("B391", "101B")
sheet.set("A392", "184369"); sheet.set("B392", "Ì@")
sheet.set("A393", "2366619632"); sheet.set("B393", "?À")
sheet.set("A394", "2366619632"); sheet.set("B394", "?Á")
sheet.set("A395", "2366619632"); sheet.set("B395", "?Â")
sheet.set("A396", "2366619632"); sheet.set("B396", "?Ã")
sheet.set("A397", "2366619632"); sheet.set("B397", "?Ä")
sheet.set("A398", "2366619632"); sheet.set("B398", "?Å")
sheet.set("A399", "2366619632"); sheet.set("B399", "?Æ")
sheet.set("A400", "2366619632"); sheet.set("B400", "?Ç")
sheet.set("A401", "2366619632"); sheet.set("B401", "?È")
sheet.set("A402", "2366619632"); sheet.set("B402", "?É")
sheet.set("A403", "2366619632"); sheet.set("B403", "?Ê")
sheet.set("A404", "2366619632"); sheet.set("B404", "?Ë")
sheet.set("A405", "2366619632"); sheet.set("B405", "?Ì")
sheet.set("A406", "2366619632"); sheet.set("B406", "?Í")
sheet.set("A407", "2366619632"); sheet.set("B407", "?Î")
sheet.set("A408", "2366619632"); sheet.set("B408", "?Ï")
sheet.set("A409", "2366619632"); sheet.set("B409", "?Ð")
sheet.set("A410", "2366619632"); sheet.set("B410", "?Ñ")
sheet.set("A411", "2366619632"); sheet.set("B411", "?Ò")
sheet.set("A412", "2366619632"); sheet.set("B412", "?Ó")
sheet.set("A413", "2366619632"); sheet.set("B413", "?Ô")
sheet.set("A414", "2366619632"); sheet.set("B414", "?Õ")
sheet.set("A415", "2366619632"); sheet.set("B415", "?Ö")
sheet.set("A416", "2366619632"); sheet.set("B416", "?×")
sheet.set("A417", "2366619632"); sheet.set("B417", "?Ø")
sheet.set("A418", "2366619632"); sheet.set("B418", "?Ú")
sheet.set("A419", "2366619632"); sheet.set("B419", "?Û")
sheet.set("A420", "2366619632"); sheet.set("B420", "?Ü")
sheet.set("A421", "2366619632"); sheet.set("B421", "?Ý")
sheet.set("A422", "2366619632"); sheet.set("B422", "?Þ")
sheet.set("A423", "2366619632"); sheet.set("B423", "?ß")
sheet.set("A424", "2366619632"); sheet.set("B424", "?à")
sheet.set("A425", "2366619632"); sheet.set("B425", "?á")
sheet.set("A426", "2366619632"); sheet.set("B426", "?â")
sheet.set("A427", "2366619632"); sheet.set("B427", "?ã")
sheet.set("A428", "2366619632"); sheet.set("B428", "?ä")
sheet.set("A429", "2366619632"); sheet.set("B429", "?å")
sheet.set("A430", "2366619632"); sheet.set("B430", "?æ")
sheet.set("A431", "2366619632"); sheet.set("B431", "?ç")
sheet.set("A432", "2366619632"); sheet.set("B432", "?è")
sheet.set("A433", "2366619632"); sheet.set("B433", "?é")
sheet.set("A434", "2366619632"); sheet.set("B434", "?ê")
sheet.set("A435", "2366619632"); sheet.set("B435", "?ë")
sheet.set("A436", "2366619632"); sheet.set("B436", "?ì")
sheet.set("A437", "2366619632"); sheet.set("B437", "?í")
sheet.set("A438", "2366619632"); sheet.set("B438", "?î")
sheet.set("A439", "2366619632"); sheet.set("B439", "?ï")
sheet.set("A440", "2366619632"); sheet.set("B440", "?ð")
sheet.set("A441", "2366619632"); sheet.set("B441", "?ñ")
sheet.set("A442", "2366619632"); sheet.set("B442", "?ò")
sheet.set("A443", "2366619632"); sheet.set("B443", "?ó")
sheet.set("A444", "2366619632"); sheet.set("B444", "?ô")
sheet.set("A445", "2366619632"); sheet.set("B445", "?õ")
sheet.set("A446", "2366619632"); sheet.set("B446", "?ö")
sheet.set("A447", "2366619632"); sheet.set("B447", "?÷")
sheet.set("A448", "2366619632"); sheet.set("B448", "?ø")
sheet.set("A449", "2366619632"); sheet.set("B449", "?ù")
sheet.set("A450", "2366619632"); sheet.set("B450", "?ú")
sheet.set("A451", "2366619632"); sheet.set("B451", "?û")
sheet.set("A452", "2366619632"); sheet.set("B452", "?ü")
sheet.set("A453", "2366619632"); sheet.set("B453", "?ý")
sheet.set("A454", "2366619632"); sheet.set("B454", "?þ")
sheet.set("A455", "2366619632"); sheet.set("B455", "?ÿ")
sheet.set("A456", "186692"); sheet.set("B456", "$@")
sheet.set("A457", "186694"); sheet.set("B457", "$@")
sheet.set("A458", "187331"); sheet.set("B458", "38")
sheet.set("A459", "187333"); sheet.set("B459", "39")
sheet.set("A460", "187335"); sheet.set("B460", "40")
sheet.set("A461", "187337"); sheet.set("B461", "41")
sheet.set("A462", "187339"); sheet.set("B462", "42")
sheet.set("A463", "187341"); sheet.set("B463", "43")
sheet.set("A464", "187343"); sheet.set("B464", "44")
sheet.set("A465", "187386"); sheet.set("B465", "45")
sheet.set("A466", "192751"); sheet.set("B466", "M_Metal Parapet Cap")
sheet.set("A467", "192754"); sheet.set("B467", "ÿC")
sheet.set("A468", "192755"); sheet.set("B468", "ÿC")
sheet.set("A469", "192756"); sheet.set("B469", "ÿC")
sheet.set("A470", "192757"); sheet.set("B470", "ÿC")
sheet.set("A471", "192758"); sheet.set("B471", "ÿC")
sheet.set("A472", "192759"); sheet.set("B472", "ÿC")
sheet.set("A473", "192760"); sheet.set("B473", "ÿC")
sheet.set("A474", "192761"); sheet.set("B474", "ÿC")
sheet.set("A475", "194632"); sheet.set("B475", "ÿL")
sheet.set("A476", "194786"); sheet.set("B476", "ÿL")
sheet.set("A477", "195035"); sheet.set("B477", "121")
sheet.set("A478", "195801"); sheet.set("B478", "ÿL")
sheet.set("A479", "195610"); sheet.set("B479", "???")
sheet.set("A480", "195801"); sheet.set("B480", "!M")
sheet.set("A481", "195624"); sheet.set("B481", "]0")
sheet.set("A482", "195610"); sheet.set("B482", "???")
sheet.set("A483", "195801"); sheet.set("B483", "!M")
sheet.set("A484", "196468"); sheet.set("B484", "101A")
sheet.set("A485", "196713"); sheet.set("B485", "ÿÐ")
sheet.set("A486", "196728"); sheet.set("B486", "101C")
sheet.set("A487", "196838"); sheet.set("B487", "101D")
sheet.set("A488", "197866"); sheet.set("B488", "Ñ@")
sheet.set("A489", "197869"); sheet.set("B489", "Ñ@")
sheet.set("A490", "198054"); sheet.set("B490", "120")
sheet.set("A491", "198553"); sheet.set("B491", "ÿ\"")
sheet.set("A492", "198563"); sheet.set("B492", "ÿ\"")
sheet.set("A493", "198605"); sheet.set("B493", "ÿ*")
sheet.set("A494", "198996"); sheet.set("B494", "11")
sheet.set("A495", "199047"); sheet.set("B495", "12")
sheet.set("A496", "199097"); sheet.set("B496", "13")
sheet.set("A497", "199141"); sheet.set("B497", "14")
sheet.set("A498", "199187"); sheet.set("B498", "15")
sheet.set("A499", "199217"); sheet.set("B499", "16")
sheet.set("A500", "199255"); sheet.set("B500", "17")
sheet.set("A501", "199291"); sheet.set("B501", "18")
sheet.set("A502", "199317"); sheet.set("B502", "19")
sheet.set("A503", "199360"); sheet.set("B503", "20")
sheet.set("A504", "199402"); sheet.set("B504", "21")
sheet.set("A505", "199436"); sheet.set("B505", "22")
sheet.set("A506", "199468"); sheet.set("B506", "23")
sheet.set("A507", "199510"); sheet.set("B507", "24")
sheet.set("A508", "199558"); sheet.set("B508", "25")
sheet.set("A509", "199584"); sheet.set("B509", "26")
sheet.set("A510", "199614"); sheet.set("B510", "27")
sheet.set("A511", "199640"); sheet.set("B511", "28")
sheet.set("A512", "200511"); sheet.set("B512", "SHADE SUPP")
sheet.set("A513", "201262"); sheet.set("B513", "ÿ:")
sheet.set("A514", "201284"); sheet.set("B514", "Curved Beam")
sheet.set("A515", "201286"); sheet.set("B515", "ÿ2")
sheet.set("A516", "201288"); sheet.set("B516", "Profile plane")
sheet.set("A517", "201306"); sheet.set("B517", "ÿB")
sheet.set("A518", "201344"); sheet.set("B518", "ÿ:")
sheet.set("A519", "206325"); sheet.set("B519", "À ")
sheet.set("A520", "206326"); sheet.set("B520", "À ")
sheet.set("A521", "206379"); sheet.set("B521", "À ")
sheet.set("A522", "212015"); sheet.set("B522", "Ì@")
sheet.set("A523", "212675"); sheet.set("B523", "ÿO")
sheet.set("A524", "213100"); sheet.set("B524", "ÿ*")
sheet.set("A525", "213108"); sheet.set("B525", "Sections")
sheet.set("A526", "214958"); sheet.set("B526", "201")
sheet.set("A527", "215097"); sheet.set("B527", "211")
sheet.set("A528", "215099"); sheet.set("B528", "212")
sheet.set("A529", "215101"); sheet.set("B529", "214")
sheet.set("A530", "215103"); sheet.set("B530", "216")
sheet.set("A531", "215105"); sheet.set("B531", "217")
sheet.set("A532", "215118"); sheet.set("B532", "218")
sheet.set("A533", "215120"); sheet.set("B533", "219")
sheet.set("A534", "215122"); sheet.set("B534", "220")
sheet.set("A535", "215124"); sheet.set("B535", "221")
sheet.set("A536", "215138"); sheet.set("B536", "222")
sheet.set("A537", "215140"); sheet.set("B537", "223")
sheet.set("A538", "215167"); sheet.set("B538", "224")
sheet.set("A539", "215169"); sheet.set("B539", "225")
sheet.set("A540", "215171"); sheet.set("B540", "226")
sheet.set("A541", "215173"); sheet.set("B541", "227")
sheet.set("A542", "215175"); sheet.set("B542", "228")
sheet.set("A543", "215177"); sheet.set("B543", "229")
sheet.set("A544", "215179"); sheet.set("B544", "230")
sheet.set("A545", "215192"); sheet.set("B545", "231")
sheet.set("A546", "215194"); sheet.set("B546", "232")
sheet.set("A547", "215196"); sheet.set("B547", "233")
sheet.set("A548", "215198"); sheet.set("B548", "234")
sheet.set("A549", "215241"); sheet.set("B549", "301")
sheet.set("A550", "215247"); sheet.set("B550", "302")
sheet.set("A551", "215249"); sheet.set("B551", "303")
sheet.set("A552", "216393"); sheet.set("B552", "304")
sheet.set("A553", "216413"); sheet.set("B553", "305")
sheet.set("A554", "216415"); sheet.set("B554", "306")
sheet.set("A555", "216417"); sheet.set("B555", "307")
sheet.set("A556", "216419"); sheet.set("B556", "308")
sheet.set("A557", "216421"); sheet.set("B557", "309")
sheet.set("A558", "216423"); sheet.set("B558", "310")
sheet.set("A559", "216433"); sheet.set("B559", "312")
sheet.set("A560", "216438"); sheet.set("B560", "313")
sheet.set("A561", "216440"); sheet.set("B561", "314")
sheet.set("A562", "216442"); sheet.set("B562", "315")
sheet.set("A563", "216444"); sheet.set("B563", "316")
sheet.set("A564", "216446"); sheet.set("B564", "317")
sheet.set("A565", "216455"); sheet.set("B565", "318")
sheet.set("A566", "216457"); sheet.set("B566", "319")
sheet.set("A567", "216459"); sheet.set("B567", "320")
sheet.set("A568", "216461"); sheet.set("B568", "321")
sheet.set("A569", "216463"); sheet.set("B569", "322")
sheet.set("A570", "216465"); sheet.set("B570", "323")
sheet.set("A571", "216467"); sheet.set("B571", "324")
sheet.set("A572", "217810"); sheet.set("B572", "206")
sheet.set("A573", "217811"); sheet.set("B573", "207")
sheet.set("A574", "217812"); sheet.set("B574", "208")
sheet.set("A575", "217813"); sheet.set("B575", "209")
sheet.set("A576", "217842"); sheet.set("B576", "ÿY")
sheet.set("A577", "219374"); sheet.set("B577", "100x200x200mm")
sheet.set("A578", "219376"); sheet.set("B578", "50x200x200mm")
sheet.set("A579", "219378"); sheet.set("B579", "150x200x200mm")
sheet.set("A580", "219380"); sheet.set("B580", "200x200x200mm")
sheet.set("A581", "219382"); sheet.set("B581", "100x100x400mm")
sheet.set("A582", "219384"); sheet.set("B582", "150x100x400mm")
sheet.set("A583", "219386"); sheet.set("B583", "200x100x400mm")
sheet.set("A584", "219388"); sheet.set("B584", "50x200x400mm")
sheet.set("A585", "219390"); sheet.set("B585", "100x200x400mm")
sheet.set("A586", "219392"); sheet.set("B586", "150x200x400mm")
sheet.set("A587", "219394"); sheet.set("B587", "04220.A16")
sheet.set("A588", "219396"); sheet.set("B588", "250x200x400mm")
sheet.set("A589", "219398"); sheet.set("B589", "300x200x400mm")
sheet.set("A590", "220116"); sheet.set("B590", "Under Slab")
sheet.set("A591", "221468"); sheet.set("B591", "#_3")
sheet.set("A592", "221470"); sheet.set("B592", "#_5")
sheet.set("A593", "221564"); sheet.set("B593", "êÀ")
sheet.set("A594", "221621"); sheet.set("B594", "Starter Track")
sheet.set("A595", "225006"); sheet.set("B595", "1200 x 150mm")
sheet.set("A596", "225008"); sheet.set("B596", "03410.C10")
sheet.set("A597", "225010"); sheet.set("B597", "1200 x 250mm")
sheet.set("A598", "225012"); sheet.set("B598", "1200 x 300mm")
sheet.set("A599", "225014"); sheet.set("B599", "1000 x 150mm")
sheet.set("A600", "225016"); sheet.set("B600", "1500 x 150mm")
sheet.set("A601", "225018"); sheet.set("B601", "1000 x 200mm")
sheet.set("A602", "225020"); sheet.set("B602", "1500 x 200mm")
sheet.set("A603", "225022"); sheet.set("B603", "1000 x 250mm")
sheet.set("A604", "225024"); sheet.set("B604", "1500 x 250mm")
sheet.set("A605", "225026"); sheet.set("B605", "1000 x 300mm")
sheet.set("A606", "225028"); sheet.set("B606", "1500 x 300mm")
sheet.set("A607", "226089"); sheet.set("B607", "150x100x100mm")
sheet.set("A608", "226091"); sheet.set("B608", "250x100x100mm")
sheet.set("A609", "226093"); sheet.set("B609", "175x100x100mm")
sheet.set("A610", "226095"); sheet.set("B610", "200x100x100mm")
sheet.set("A611", "226097"); sheet.set("B611", "07620.B1")
sheet.set("A612", "226618"); sheet.set("B612", "06110.A2")
sheet.set("A613", "227999"); sheet.set("B613", "13mm")
sheet.set("A614", "228001"); sheet.set("B614", "25mm")
sheet.set("A615", "228003"); sheet.set("B615", "38mm")
sheet.set("A616", "228005"); sheet.set("B616", "50mm")
sheet.set("A617", "228007"); sheet.set("B617", "75mm")
sheet.set("A618", "228009"); sheet.set("B618", "63mm")
sheet.set("A619", "228070"); sheet.set("B619", "07210.B6")
sheet.set("A620", "228871"); sheet.set("B620", "From Parking Area")
sheet.set("A621", "233078"); sheet.set("B621", "03 - Floor Publi")
sheet.set("A622", "234689"); sheet.set("B622", "W@")
sheet.set("A623", "234691"); sheet.set("B623", "W@")
sheet.set("A624", "235371"); sheet.set("B624", "67")
sheet.set("A625", "235372"); sheet.set("B625", "68")
sheet.set("A626", "235373"); sheet.set("B626", "69")
sheet.set("A627", "235374"); sheet.set("B627", "70")
sheet.set("A628", "240060"); sheet.set("B628", "ÿT")
sheet.set("A629", "240065"); sheet.set("B629", "ÿ{")
sheet.set("A630", "240069"); sheet.set("B630", "ÿ]")
sheet.set("A631", "240084"); sheet.set("B631", "ÿ{")
sheet.set("A632", "240849"); sheet.set("B632", "47")
sheet.set("A633", "240851"); sheet.set("B633", "48")
sheet.set("A634", "240851"); sheet.set("B634", "48")
sheet.set("A635", "240853"); sheet.set("B635", "49")
sheet.set("A636", "240855"); sheet.set("B636", "50")
sheet.set("A637", "240857"); sheet.set("B637", "51")
sheet.set("A638", "240859"); sheet.set("B638", "52")
sheet.set("A639", "240861"); sheet.set("B639", "53")
sheet.set("A640", "241445"); sheet.set("B640", "54")
sheet.set("A641", "241447"); sheet.set("B641", "55")
sheet.set("A642", "241449"); sheet.set("B642", "56")
sheet.set("A643", "241451"); sheet.set("B643", "57")
sheet.set("A644", "241453"); sheet.set("B644", "58")
sheet.set("A645", "241455"); sheet.set("B645", "59")
sheet.set("A646", "241457"); sheet.set("B646", "60")
sheet.set("A647", "242099"); sheet.set("B647", "61")
sheet.set("A648", "242101"); sheet.set("B648", "62")
sheet.set("A649", "242103"); sheet.set("B649", "63")
sheet.set("A650", "242105"); sheet.set("B650", "64")
sheet.set("A651", "242107"); sheet.set("B651", "65")
sheet.set("A652", "243204"); sheet.set("B652", "12")
sheet.set("A653", "243663"); sheet.set("B653", "10")
sheet.set("A654", "243713"); sheet.set("B654", "11")
sheet.set("A655", "243714"); sheet.set("B655", "13")
sheet.set("A656", "243764"); sheet.set("B656", "14")
sheet.set("A657", "243765"); sheet.set("B657", "15")
sheet.set("A658", "243815"); sheet.set("B658", "16")
sheet.set("A659", "243816"); sheet.set("B659", "17")
sheet.set("A660", "245151"); sheet.set("B660", "21")
sheet.set("A661", "245152"); sheet.set("B661", "B2010")
sheet.set("A662", "245907"); sheet.set("B662", "18")
sheet.set("A663", "245958"); sheet.set("B663", "19")
sheet.set("A664", "246011"); sheet.set("B664", "20")
sheet.set("A665", "246012"); sheet.set("B665", "22")
sheet.set("A666", "246033"); sheet.set("B666", "23")
sheet.set("A667", "246129"); sheet.set("B667", "24")
sheet.set("A668", "247622"); sheet.set("B668", "Wö")
sheet.set("A669", "248326"); sheet.set("B669", "37")
sheet.set("A670", "248327"); sheet.set("B670", "38")
sheet.set("A671", "248872"); sheet.set("B671", "Dwayne")
sheet.set("A672", "248874"); sheet.set("B672", "Alex")
sheet.set("A673", "248876"); sheet.set("B673", "LaRon")
sheet.set("A674", "248878"); sheet.set("B674", "Jay")
sheet.set("A675", "249430"); sheet.set("B675", "Cynthia")
sheet.set("A676", "249432"); sheet.set("B676", "Cathy")
sheet.set("A677", "249434"); sheet.set("B677", "Tina")
sheet.set("A678", "249436"); sheet.set("B678", "YinYin")
sheet.set("A679", "249438"); sheet.set("B679", "Florence")
sheet.set("A680", "249440"); sheet.set("B680", "Lisa")
sheet.set("A681", "249631"); sheet.set("B681", "03 - Floor Publi")
sheet.set("A682", "252344"); sheet.set("B682", "Elevation Mark Pointer_Square")
sheet.set("A683", "252620"); sheet.set("B683", "Elevation Mark Square - Upgra")
sheet.set("A684", "252880"); sheet.set("B684", "Elevation Mark Pointer_Circle")
sheet.set("A685", "252893"); sheet.set("B685", "Type 1")
sheet.set("A686", "252894"); sheet.set("B686", "Type 2")
sheet.set("A687", "253190"); sheet.set("B687", "12mm Circle")
sheet.set("A688", "253194"); sheet.set("B688", "10mm Circle")
sheet.set("A689", "254825"); sheet.set("B689", "(5")
sheet.set("A690", "258326"); sheet.set("B690", "EQ")
sheet.set("A691", "414"); sheet.set("B691", "Masonry - Brick")
sheet.set("A692", "415"); sheet.set("B692", "Masonry - Concrete Block")
sheet.set("A693", "416"); sheet.set("B693", "Metal - Stud Layer")
sheet.set("A694", "417"); sheet.set("B694", "Wood - Sheathing - plywood")
sheet.set("A695", "418"); sheet.set("B695", "Misc. Air Layers - Air Space")
sheet.set("A696", "419"); sheet.set("B696", "Air Barrier - Air Infiltration Barrier")
sheet.set("A697", "420"); sheet.set("B697", "Insulation / Thermal Barriers - Rigid insulation")
sheet.set("A698", "421"); sheet.set("B698", "Vapour / Moisture Barriers - Vapour Retarder")
sheet.set("A699", "422"); sheet.set("B699", "Vapour / Moisture Barriers - Damp-proofing")
sheet.set("A700", "423"); sheet.set("B700", "Interior finish")
sheet.set("A701", "528"); sheet.set("B701", "Metal - Trim")
sheet.set("A702", "529"); sheet.set("B702", "Metal - Decking")
sheet.set("A703", "530"); sheet.set("B703", "Metal - Sheet / Flashing")
sheet.set("A704", "531"); sheet.set("B704", "Exterior finish, roofing")
sheet.set("A705", "532"); sheet.set("B705", "Metal - Steel")
sheet.set("A706", "533"); sheet.set("B706", "Metal - Aluminium")
sheet.set("A707", "534"); sheet.set("B707", "Metal - Firring")
sheet.set("A708", "535"); sheet.set("B708", "Wood - Stud Layer")
sheet.set("A709", "536"); sheet.set("B709", "Wood - Sheathing - Chipboard")
sheet.set("A710", "539"); sheet.set("B710", "Wood - Timber")
sheet.set("A711", "540"); sheet.set("B711", "Wood - Laminated")
sheet.set("A712", "542"); sheet.set("B712", "Plastic - GRP - Glass Reinforced Plastic")
sheet.set("A713", "543"); sheet.set("B713", "Plastic - Formed Plastic")
sheet.set("A714", "544"); sheet.set("B714", "Plastic - Vinyl Cove Base")
sheet.set("A715", "545"); sheet.set("B715", "Exterior finish")
sheet.set("A716", "548"); sheet.set("B716", "Exterior finish")
sheet.set("A717", "549"); sheet.set("B717", "Exterior finish, roofing")
sheet.set("A718", "550"); sheet.set("B718", "Misc. Air Layers - Air Film - Outside Surface")
sheet.set("A719", "551"); sheet.set("B719", "Misc. Air Layers - Air Film - Inside Surface")
sheet.set("A720", "552"); sheet.set("B720", "Insulation / Thermal Barriers - Batt insulation")
sheet.set("A721", "553"); sheet.set("B721", "Insulation / Thermal Barriers - Semi-rigid insulation")
sheet.set("A722", "555"); sheet.set("B722", "Insulation / Thermal Barriers - Radient Heat Barrier")
sheet.set("A723", "5658"); sheet.set("B723", "Wall Material (1)")
sheet.set("A724", "10988"); sheet.set("B724", "Sash")
sheet.set("A725", "12859"); sheet.set("B725", "Parking Stripe")
sheet.set("A726", "18744"); sheet.set("B726", "Metal - Paint Finish - Dark Gray, Matte")
sheet.set("A727", "102844"); sheet.set("B727", "1\\mats\\sitework.paving & surfacing.asphalt.png")
sheet.set("A728", "102844"); sheet.set("B728", "1\\mats\\sitework.pa")
sheet.set("A729", "102855"); sheet.set("B729", "1\\mats\\chipboard.png")
sheet.set("A730", "170392"); sheet.set("B730", "Metal - Paint Finish - Paint Cafe Matte")
sheet.set("A731", "187849"); sheet.set("B731", "Metal - Aluminum")
sheet.set("A732", "228748"); sheet.set("B732", "Metal - Aluminium, Black-Anodized")
sheet.set("A733", "240048"); sheet.set("B733", "Concrete - Precast Concrete")
sheet.set("A734", "240049"); sheet.set("B734", "1\\mats\\finishes.flooring.carpet.loop.1colour.png")
sheet.set("A735", "240050"); sheet.set("B735", "Plastic - Dark Maroon, Smooth")
sheet.set("A736", "240051"); sheet.set("B736", "1\\mats\\furnishings.fabrics.leather.pebble.brown.png")
sheet.set("A737", "240052"); sheet.set("B737", "Chrome")
sheet.set("A738", "240053"); sheet.set("B738", "Black, Glossy")
sheet.set("A739", "240055"); sheet.set("B739", "1\\mats\\furnishings.fabrics.linen.beige.png")
sheet.set("A740", "240056"); sheet.set("B740", "Metal - Bronze")
sheet.set("A741", "240071"); sheet.set("B741", "1\\mats\\furnishings.fabrics.leather.pebble.tan.png")
sheet.set("A742", "242824"); sheet.set("B742", "Interior finish")
sheet.set("A743", "245768"); sheet.set("B743", "Glass - Clear Light")
sheet.set("A744", "253872"); sheet.set("B744", "1\\mats\\sitework.paving & surfacing.asphalt.png")
sheet.set("A745", "253873"); sheet.set("B745", "1\\mats\\finishes.flooring.carpet.1.png")
sheet.set("A746", "253878"); sheet.set("B746", "1\\mats\\chipboard.png")
sheet.set("A747", "258625"); sheet.set("B747", "1\\mats\\furnishings.fabrics.linen.beige.png")
sheet.set("A748", "258627"); sheet.set("B748", "1\\mats\\furnishings.fabrics.leather.pebble.tan.png")
sheet.set("A749", "86551"); sheet.set("B749", "M_Material TagF")
sheet.set("A750", "87285"); sheet.set("B750", "M_Area Tag8")
sheet.set("A751", "87489"); sheet.set("B751", "M_Callout Head8")
sheet.set("A752", "87690"); sheet.set("B752", "M_Centreline8")
sheet.set("A753", "87880"); sheet.set("B753", "M_Door TagF")
sheet.set("A754", "88069"); sheet.set("B754", "M_Grid Head - Circle8")
sheet.set("A755", "88264"); sheet.set("B755", "M_Grid Head - No Bubble8")
sheet.set("A756", "88459"); sheet.set("B756", "M_Level Head - Circle8")
sheet.set("A757", "88868"); sheet.set("B757", "M_North Arrow-28")
sheet.set("A758", "89062"); sheet.set("B758", "M_Room Tag8")
sheet.set("A759", "89267"); sheet.set("B759", "M_Section Head - Filled8")
sheet.set("A760", "89493"); sheet.set("B760", "M_Section Head - No Arrow8")
sheet.set("A761", "89695"); sheet.set("B761", "M_Section Head - Open8")
sheet.set("A762", "89897"); sheet.set("B762", "M_Section Tail - Filled8")
sheet.set("A763", "90110"); sheet.set("B763", "M_Section Tail - Filled Horizontal8")
sheet.set("A764", "90323"); sheet.set("B764", "M_Spot Elevation - Exterior Filled8")
sheet.set("A765", "90520"); sheet.set("B765", "M_Spot Elevation - Target Filled8")
sheet.set("A766", "90722"); sheet.set("B766", "M_View Title8")
sheet.set("A767", "90915"); sheet.set("B767", "M_Wall TagF")
sheet.set("A768", "91112"); sheet.set("B768", "M_Window TagF")
sheet.set("A769", "99945"); sheet.set("B769", "M_View Reference8")
sheet.set("A770", "100195"); sheet.set("B770", "M_Spot Elevation - Crosshair:")
sheet.set("A771", "102134"); sheet.set("B771", "M_Revision Tag8")
sheet.set("A772", "111696"); sheet.set("B772", "M_Property Line Tagh")
sheet.set("A773", "157138"); sheet.set("B773", "Level Head - Circle:")
sheet.set("A774", "221668"); sheet.set("B774", "View Title:")
sheet.set("A775", "221894"); sheet.set("B775", "Callout Head:")
sheet.set("A776", "222099"); sheet.set("B776", "Section Head - Filled:")
sheet.set("A777", "222324"); sheet.set("B777", "Section Head - no arrow:")
sheet.set("A778", "222521"); sheet.set("B778", "Section Head - Open:")
sheet.set("A779", "222722"); sheet.set("B779", "Section Tail - Filled:")
sheet.set("A780", "222932"); sheet.set("B780", "Section Tail - Filled Horizontal:")
sheet.set("A781", "252077"); sheet.set("B781", "Elevation Mark Square - Upgrade#")
sheet.set("A782", "252346"); sheet.set("B782", "Elevation Mark Pointer_SquareE")
sheet.set("A783", "252622"); sheet.set("B783", "Elevation Mark Circle - Upgrade#")
sheet.set("A784", "252901"); sheet.set("B784", "Elevation Mark Pointer_CircleM")
sheet.set("A785", "270592"); sheet.set("B785", "A1 metric")
sheet.set("A786", "270596"); sheet.set("B786", "Arrow 30 Degree")
sheet.set("A787", "270598"); sheet.set("B787", "8mm")
sheet.set("A788", "94874"); sheet.set("B788", "M_Fascia-Flat;")
sheet.set("A789", "95100"); sheet.set("B789", "M_Gutter - Bevel;")
sheet.set("A790", "95353"); sheet.set("B790", "M_Reveal-Brick Course5")
sheet.set("A791", "95577"); sheet.set("B791", "M_Slab Edge-Thickened@")
sheet.set("A792", "95803"); sheet.set("B792", "M_Baluster - RoundD")
sheet.set("A793", "96261"); sheet.set("B793", "M_Baluster - SquareD")
sheet.set("A794", "96718"); sheet.set("B794", "UC-Universal Column-ColumnE")
sheet.set("A795", "98188"); sheet.set("B795", "M_FixedB")
sheet.set("A796", "101148"); sheet.set("B796", "UB-Universal BeamE")
sheet.set("A797", "102903"); sheet.set("B797", "M_Desk-")
sheet.set("A798", "104584"); sheet.set("B798", "M_RPC Tree - Deciduous+")
sheet.set("A799", "134098"); sheet.set("B799", "M_RPC Shrub_")
sheet.set("A800", "140468"); sheet.set("B800", "M_Concrete-Round-Columnr")
sheet.set("A801", "146838"); sheet.set("B801", "M_Double-Flush\\")
sheet.set("A802", "170864"); sheet.set("B802", "Circular Handrail>")
sheet.set("A803", "171080"); sheet.set("B803", "Stair Nosing - Pan>")
sheet.set("A804", "173781"); sheet.set("B804", "Handrail - Round w Extension - Start-Offset~")
sheet.set("A805", "174326"); sheet.set("B805", "Handrail - Bracket~")
sheet.set("A806", "174951"); sheet.set("B806", "Handrail - Round w Extension - End~")
sheet.set("A807", "175724"); sheet.set("B807", "Rectangular Handrail>")
sheet.set("A808", "176427"); sheet.set("B808", "Baluster - RoundF")
sheet.set("A809", "179716"); sheet.set("B809", "M_Chair-Breuer-")
sheet.set("A810", "186791"); sheet.set("B810", "M_Single-Flush-Dbl Acting\\")
sheet.set("A811", "187782"); sheet.set("B811", "M_Curtain Wall Dbl Glass\\")
sheet.set("A812", "192426"); sheet.set("B812", "M_Metal Parapet Capy")
sheet.set("A813", "194085"); sheet.set("B813", "M_Curtain Wall Sgl Glass\\")
sheet.set("A814", "199677"); sheet.set("B814", "SHADE SUPPORT")
sheet.set("A815", "199677"); sheet.set("B815", "Re")
sheet.set("A816", "199677"); sheet.set("B816", "Re")
sheet.set("A817", "199677"); sheet.set("B817", "Re")
sheet.set("A818", "199677"); sheet.set("B818", "Of")
sheet.set("A819", "199677"); sheet.set("B819", "09\\Metri")
sheet.set("A820", "199677"); sheet.set("B820", "09\\Metri")
sheet.set("A821", "199677"); sheet.set("B821", "09\\Metri")
sheet.set("A822", "199677"); sheet.set("B822", "09\\Metri")
sheet.set("A823", "199677"); sheet.set("B823", "09\\Metri")
sheet.set("A824", "199677"); sheet.set("B824", "09\\Metri")
sheet.set("A825", "199677"); sheet.set("B825", "09\\Metri")
sheet.set("A826", "223299"); sheet.set("B826", "M_Break Linew")
sheet.set("A827", "224466"); sheet.set("B827", "M_Precast Slab-Hollow Core-Side")
sheet.set("A828", "225750"); sheet.set("B828", "M_Coping-SectionÈ")
sheet.set("A829", "226335"); sheet.set("B829", "Cant Strip-Wood-SectionË")
sheet.set("A830", "226688"); sheet.set("B830", "M_Tapered Rigid Insulation-SectionÂ")
sheet.set("A831", "227720"); sheet.set("B831", "M_Rigid Insulation-SectionÂ")
sheet.set("A832", "235381"); sheet.set("B832", "Chair-ViperX")
sheet.set("A833", "236087"); sheet.set("B833", "Couch-ViperX")
sheet.set("A834", "236786"); sheet.set("B834", "Table-Night StandX")
sheet.set("A835", "237301"); sheet.set("B835", "Potted Plant<")
sheet.set("A836", "239032"); sheet.set("B836", "Wastebasket2X")
sheet.set("A837", "239471"); sheet.set("B837", "Table Lamp 4X")
sheet.set("A838", "240295"); sheet.set("B838", "M_Single-Flush Vision\\")
sheet.set("A839", "240863"); sheet.set("B839", "M_Single-Glass 1\\")
sheet.set("A840", "241459"); sheet.set("B840", "M_Double-Glass 1\\")
sheet.set("A841", "242245"); sheet.set("B841", "Pendant Light - Linear - 1 Lampj")
sheet.set("A842", "245154"); sheet.set("B842", "Sconce 4+")
sheet.set("A843", "246174"); sheet.set("B843", "Window Shade2")
sheet.set("A844", "248458"); sheet.set("B844", "M_RPC Male`")
sheet.set("A845", "249019"); sheet.set("B845", "M_RPC Female`")
sheet.set("A846", "8482"); sheet.set("B846", "Rectangular Mullion")
sheet.set("A847", "8483"); sheet.set("B847", "Circular Mullion")
sheet.set("A848", "12609"); sheet.set("B848", "System Panel")
sheet.set("A849", "12613"); sheet.set("B849", "Empty System Panel")
sheet.set("A850", "18428"); sheet.set("B850", "L Corner Mullion")
sheet.set("A851", "18432"); sheet.set("B851", "V Corner Mullion")
sheet.set("A852", "18436"); sheet.set("B852", "Trapezoid Corner Mullion")
sheet.set("A853", "18440"); sheet.set("B853", "Quad Corner Mullion")
sheet.set("A854", "240068"); sheet.set("B854", "C:\\Documents and Settings\\hansonje\\Desktop\\Newspaper.jpg")
sheet.set("A855", "253835"); sheet.set("B855", "1\\Mats\\Masonry.Stone.Ashlar.Random.Broken Coursed.png")
sheet.set("A856", "253836"); sheet.set("B856", "1\\Mats\\Masonry.Stone.Slate.png")
sheet.set("A857", "253839"); sheet.set("B857", "1\\Mats\\tempWood_for_Elm.png")
sheet.set("A858", "253840"); sheet.set("B858", "1\\Mats\\beechwood_galliano.png")
sheet.set("A859", "253842"); sheet.set("B859", "1\\Mats\\Woods & Plastics.Finish Carpentry.Wood.Pine.png")
sheet.set("A860", "253845"); sheet.set("B860", "1\\Mats\\283.png")
sheet.set("A861", "253846"); sheet.set("B861", "1\\Mats\\Concrete.Precast Structural Concrete.Smooth.png")
sheet.set("A862", "253848"); sheet.set("B862", "1\\Mats\\272.png")
sheet.set("A863", "253850"); sheet.set("B863", "1\\Mats\\plastic_Course_bump.png")
sheet.set("A864", "253857"); sheet.set("B864", "1\\Mats\\Woods & Plastics.Finish Carpentry.Wood.Maple.png")
sheet.set("A865", "253888"); sheet.set("B865", "1\\Mats\\Masonry.Stone.Granite.Square.Copper-Black-Blue.png")
sheet.set("A866", "253890"); sheet.set("B866", "1\\Mats\\Metals.Ornamental Metals.Plate.Mesh.cutout.png")
sheet.set("A867", "253893"); sheet.set("B867", "1\\Mats\\Finishes.Flooring.Carpet.Loop.1Colour.png")
sheet.set("A868", "253895"); sheet.set("B868", "1\\Mats\\Furnishings.Fabrics.Leather.Pebble.Brown.png")
sheet.set("A869", "253896"); sheet.set("B869", "1\\Mats\\Furnishings.Fabrics.Linen.Beige.png")
sheet.set("A870", "253898"); sheet.set("B870", "1\\Mats\\Furnishings.Fabrics.Leather.Pebble.Tan.png")
sheet.set("A871", "247987"); sheet.set("B871", "Array Group 9")
sheet.set("A872", "142294"); sheet.set("B872", "Concrete Deck - Tapered Insulation")
sheet.set("A873", "242823"); sheet.set("B873", "C3030220")
sheet.set("A874", "243361"); sheet.set("B874", "Array Group 8")
sheet.set("A875", "157602"); sheet.set("B875", "Hollow Core Plank - Concrete Topping")
sheet.set("A876", "240057"); sheet.set("B876", "B1010")
sheet.set("A877", "228722"); sheet.set("B877", "Roofing Detail.dwg")
sheet.set("A878", "228723"); sheet.set("B878", "Roofing Detail.dwg.FSBP_AP_FASTENER_02")
sheet.set("A879", "228724"); sheet.set("B879", "Roofing Detail.dwg._OBLIQUE")
sheet.set("A880", "224039"); sheet.set("B880", "Concrete")
sheet.set("A881", "130735"); sheet.set("B881", "Pad 1")
sheet.set("A882", "217836"); sheet.set("B882", "Concrete- 100mm")
sheet.set("A883", "201366"); sheet.set("B883", "B1020")
sheet.set("A884", "200609"); sheet.set("B884", "Array Group 4")
sheet.set("A885", "200742"); sheet.set("B885", "Array Group 5")
sheet.set("A886", "200829"); sheet.set("B886", "Array Group 6")
sheet.set("A887", "200905"); sheet.set("B887", "Array Group 7")
sheet.set("A888", "200936"); sheet.set("B888", "B1010")
sheet.set("A889", "186910"); sheet.set("B889", "Dashed Line")
sheet.set("A890", "186911"); sheet.set("B890", "ÿl")
sheet.set("A891", "180535"); sheet.set("B891", "Array Group 3")
sheet.set("A892", "784"); sheet.set("B892", "Standard Timber-Wood Finish")
sheet.set("A893", "23763"); sheet.set("B893", "EQ")
sheet.set("A894", "23766"); sheet.set("B894", "Arial")
sheet.set("A895", "23772"); sheet.set("B895", "5480 x 2740mm - 90 deg")
sheet.set("A896", "132025"); sheet.set("B896", "Array Group 1")
sheet.set("A897", "133306"); sheet.set("B897", "Array Group 2")
sheet.set("A898", "785"); sheet.set("B898", "Beam and Block 200mm")
sheet.set("A899", "786"); sheet.set("B899", "Insitu Concrete 225mm")
sheet.set("A900", "5113"); sheet.set("B900", "Concrete-Domestic 425mm")
sheet.set("A901", "19847"); sheet.set("B901", "600 x 1200mm Grid")
sheet.set("A902", "19848"); sheet.set("B902", "600 x 600mm Grid")
sheet.set("A903", "88900"); sheet.set("B903", "Enter new name here")
sheet.set("A904", "88901"); sheet.set("B904", "M_North Arrow-2")
sheet.set("A905", "86313"); sheet.set("B905", "150mm Foundation Slab")
sheet.set("A906", "23773"); sheet.set("B906", "SecretInternalTypePreviewgArrowhead5478765182")
sheet.set("A907", "23775"); sheet.set("B907", "ÿl")
sheet.set("A908", "335"); sheet.set("B908", "Generic - 400mm")
sheet.set("A909", "337"); sheet.set("B909", "Generic - 125mm")
sheet.set("A910", "339"); sheet.set("B910", "Generic 150mm")
sheet.set("A911", "759"); sheet.set("B911", "Generic 300mm")
sheet.set("A912", "18928"); sheet.set("B912", "Generic 150mm - Filled")
sheet.set("A913", "18934"); sheet.set("B913", "Generic - 400mm - Filled")
sheet.set("A914", "19878"); sheet.set("B914", "Generic - 300mm")
sheet.set("A915", "5173"); sheet.set("B915", "Warm Roof - Timber")
sheet.set("A916", "8612"); sheet.set("B916", "North Line")
sheet.set("A917", "8616"); sheet.set("B917", "Medium Line")
sheet.set("A918", "8618"); sheet.set("B918", "Thin Line")
sheet.set("A919", "8619"); sheet.set("B919", "ÿl")
sheet.set("A920", "757"); sheet.set("B920", "Generic")
sheet.set("A921", "19849"); sheet.set("B921", "Plain")
sheet.set("A922", "277"); sheet.set("B922", "EQ")
sheet.set("A923", "280"); sheet.set("B923", "Arial")
sheet.set("A924", "288"); sheet.set("B924", "EQ")
sheet.set("A925", "291"); sheet.set("B925", "Arial")
sheet.set("A926", "293"); sheet.set("B926", "ÿl")
sheet.set("A927", "18454"); sheet.set("B927", "ÿl")
sheet.set("A928", "336"); sheet.set("B928", "Steel Bar Joist - Steel Deck - EPDM Membrane")
sheet.set("A929", "880"); sheet.set("B929", "Cold Roof - Concrete ")
sheet.set("A930", "5136"); sheet.set("B930", "Concrete-Commercial 362mm")
sheet.set("A931", "5165"); sheet.set("B931", "Warm Roof - Concrete")
sheet.set("A932", "3443"); sheet.set("B932", "Medium Lines")
sheet.set("A933", "3444"); sheet.set("B933", "Trim")
sheet.set("A934", "285"); sheet.set("B934", "SecretInternalLinAngArrowhead547r36186")
sheet.set("A935", "296"); sheet.set("B935", "SecretInternalRadArrowhead5473s6187")
sheet.set("A936", "298"); sheet.set("B936", "Sloped Glazing")
sheet.set("A937", "425"); sheet.set("B937", "Crosshatch 1.5mm")
sheet.set("A938", "426"); sheet.set("B938", "Diagonal up 1.5mm")
sheet.set("A939", "279012"); sheet.set("B939", "EQ")
sheet.set("A940", "279015"); sheet.set("B940", "Arial")
sheet.set("A941", "279020"); sheet.set("B941", "SecretInternalLinAngArrowhead547r36186")
sheet.set("A942", "279023"); sheet.set("B942", "EQ")
sheet.set("A943", "279026"); sheet.set("B943", "Arial")
sheet.set("A944", "279031"); sheet.set("B944", "SecretInternalRadArrowhead5473s6187")
sheet.set("A945", "279034"); sheet.set("B945", "EQ")
sheet.set("A946", "279037"); sheet.set("B946", "Arial")
sheet.set("A947", "279042"); sheet.set("B947", "SecretInternalTypePreviewgArrowhead5478765182")
sheet.set("A948", "279045"); sheet.set("B948", "C:\\pf_root\\9.0\\Data\\Platform\\Metric\\Library\\Annotations\\Architectural\\")
sheet.set("A949", "279078"); sheet.set("B949", "Arial")
sheet.set("A950", "279142"); sheet.set("B950", "Revision Cloud 1{")
sheet.set("A951", "307929"); sheet.set("B951", "EQ")
sheet.set("A952", "307932"); sheet.set("B952", "Arial")
sheet.set("A953", "307937"); sheet.set("B953", "SecretInternalLinAngArrowhead547r36186")
sheet.set("A954", "307940"); sheet.set("B954", "EQ")
sheet.set("A955", "307943"); sheet.set("B955", "Arial")
sheet.set("A956", "307948"); sheet.set("B956", "SecretInternalRadArrowhead5473s6187")
sheet.set("A957", "307951"); sheet.set("B957", "EQ")
sheet.set("A958", "307954"); sheet.set("B958", "Arial")
sheet.set("A959", "307959"); sheet.set("B959", "SecretInternalTypePreviewgArrowhead5478765182")
sheet.set("A960", "307962"); sheet.set("B960", "C:\\Documents and Settings\\All Users\\Application Data\\Autodesk\\RAC 2009\\Metric Library\\Doors\\")
sheet.set("A961", "307972"); sheet.set("B961", "Ground floor")
sheet.set("A962", "307981"); sheet.set("B962", "Wall 1")
sheet.set("A963", "307982"); sheet.set("B963", "ÿ5")
sheet.set("A964", "308028"); sheet.set("B964", "View 1")
sheet.set("A965", "308062"); sheet.set("B965", "ÿ\"")
sheet.set("A966", "308105"); sheet.set("B966", "ÿ\"")
sheet.set("A967", "308123"); sheet.set("B967", "ÿ\"")
sheet.set("A968", "308141"); sheet.set("B968", "Trim Width Int.")
sheet.set("A969", "308145"); sheet.set("B969", "Trim Width Ext.")
sheet.set("A970", "308172"); sheet.set("B970", "Revealy")
sheet.set("A971", "308224"); sheet.set("B971", "Level Head - Upgrade")
sheet.set("A972", "308237"); sheet.set("B972", "Elevation 1")
sheet.set("A973", "308282"); sheet.set("B973", "Name")
sheet.set("A974", "308307"); sheet.set("B974", "Filled Elevation Target Ä")
sheet.set("A975", "308313"); sheet.set("B975", "6.35 mm")
sheet.set("A976", "279385"); sheet.set("B976", "EQ")
sheet.set("A977", "279388"); sheet.set("B977", "Arial")
sheet.set("A978", "279393"); sheet.set("B978", "SecretInternalLinAngArrowhead547r36186")
sheet.set("A979", "279396"); sheet.set("B979", "EQ")
sheet.set("A980", "279399"); sheet.set("B980", "Arial")
sheet.set("A981", "279404"); sheet.set("B981", "SecretInternalRadArrowhead5473s6187")
sheet.set("A982", "279407"); sheet.set("B982", "EQ")
sheet.set("A983", "279410"); sheet.set("B983", "Arial")
sheet.set("A984", "279415"); sheet.set("B984", "SecretInternalTypePreviewgArrowhead5478765182")
sheet.set("A985", "279418"); sheet.set("B985", "C:\\pf_root\\9.0\\Data\\Platform\\Metric\\Library\\Architectural\\Columns\\")
sheet.set("A986", "279433"); sheet.set("B986", "Ground floor")
sheet.set("A987", "279442"); sheet.set("B987", "Upper Ref Level")
sheet.set("A988", "279461"); sheet.set("B988", "Curtain Wall 1")
sheet.set("A989", "279471"); sheet.set("B989", "???")
sheet.set("A990", "279487"); sheet.set("B990", "View 1")
sheet.set("A991", "279526"); sheet.set("B991", "Revealy")
sheet.set("A992", "279568"); sheet.set("B992", "Level Head - Upgrade")
sheet.set("A993", "279581"); sheet.set("B993", "Elevation 1")
sheet.set("A994", "279626"); sheet.set("B994", "Name")
sheet.set("A995", "279651"); sheet.set("B995", "Filled Elevation Target Ä")
sheet.set("A996", "279657"); sheet.set("B996", "20.8333 mm")
sheet.set("A997", "287157"); sheet.set("B997", "EQ")
sheet.set("A998", "287160"); sheet.set("B998", "Arial")
sheet.set("A999", "287165"); sheet.set("B999", "SecretInternalLinAngArrowhead547r36186")
sheet.set("A1000", "287168"); sheet.set("B1000", "EQ")
sheet.set("A1001", "287171"); sheet.set("B1001", "Arial")
sheet.set("A1002", "287176"); sheet.set("B1002", "SecretInternalRadArrowhead5473s6187")
sheet.set("A1003", "287179"); sheet.set("B1003", "EQ")
sheet.set("A1004", "287182"); sheet.set("B1004", "Arial")
sheet.set("A1005", "287187"); sheet.set("B1005", "SecretInternalTypePreviewgArrowhead5478765182")
sheet.set("A1006", "287190"); sheet.set("B1006", "C:\\Documents and Settings\\campbes\\Desktop\\")
sheet.set("A1007", "287200"); sheet.set("B1007", "Ref. Level")
sheet.set("A1008", "287225"); sheet.set("B1008", "Center F/B")
sheet.set("A1009", "287227"); sheet.set("B1009", "Center L/R")
sheet.set("A1010", "287234"); sheet.set("B1010", "{3D}")
sheet.set("A1011", "287277"); sheet.set("B1011", "ÿG")
sheet.set("A1012", "287278"); sheet.set("B1012", "ÿà")
sheet.set("A1013", "287279"); sheet.set("B1013", "ÿà")
sheet.set("A1014", "287280"); sheet.set("B1014", "ÿà")
sheet.set("A1015", "287319"); sheet.set("B1015", "Level Head - Upgrade")
sheet.set("A1016", "287332"); sheet.set("B1016", "Elevation 1")
sheet.set("A1017", "287377"); sheet.set("B1017", "Name")
sheet.set("A1018", "287402"); sheet.set("B1018", "Filled Elevation Target Ä")
sheet.set("A1019", "287408"); sheet.set("B1019", "6.35 mm")
sheet.set("A1020", "287499"); sheet.set("B1020", "ÿà")
sheet.set("A1021", "287500"); sheet.set("B1021", "ÿà")
sheet.set("A1022", "287501"); sheet.set("B1022", "ÿà")
sheet.set("A1023", "287502"); sheet.set("B1023", "ÿà")
sheet.set("A1024", "287503"); sheet.set("B1024", "ÿà")
sheet.set("A1025", "287504"); sheet.set("B1025", "ÿà")
sheet.set("A1026", "287505"); sheet.set("B1026", "ÿà")
sheet.set("A1027", "287506"); sheet.set("B1027", "ÿà")
sheet.set("A1028", "287507"); sheet.set("B1028", "ÿà")
sheet.set("A1029", "287508"); sheet.set("B1029", "ÿà")
sheet.set("A1030", "287509"); sheet.set("B1030", "ÿà")
sheet.set("A1031", "287510"); sheet.set("B1031", "ÿà")
sheet.set("A1032", "287511"); sheet.set("B1032", "ÿà")
sheet.set("A1033", "287502"); sheet.set("B1033", "ÿà")
sheet.set("A1034", "287502"); sheet.set("B1034", "ÿà")
sheet.set("A1035", "276699"); sheet.set("B1035", "EQ")
sheet.set("A1036", "276702"); sheet.set("B1036", "Arial")
sheet.set("A1037", "276707"); sheet.set("B1037", "SecretInternalLinAngArrowhead547r36186")
sheet.set("A1038", "276710"); sheet.set("B1038", "EQ")
sheet.set("A1039", "276713"); sheet.set("B1039", "Arial")
sheet.set("A1040", "276718"); sheet.set("B1040", "SecretInternalRadArrowhead5473s6187")
sheet.set("A1041", "276721"); sheet.set("B1041", "EQ")
sheet.set("A1042", "276724"); sheet.set("B1042", "Arial")
sheet.set("A1043", "276729"); sheet.set("B1043", "SecretInternalTypePreviewgArrowhead5478765182")
sheet.set("A1044", "276732"); sheet.set("B1044", "C:\\pf_root\\9.0\\Data\\Platform\\Metric\\Library\\Annotations\\")
sheet.set("A1045", "276808"); sheet.set("B1045", "Filled Elevation Target Ä")
sheet.set("A1046", "289023"); sheet.set("B1046", "EQ")
sheet.set("A1047", "289026"); sheet.set("B1047", "Arial")
sheet.set("A1048", "289031"); sheet.set("B1048", "SecretInternalLinAngArrowhead547r36186")
sheet.set("A1049", "289034"); sheet.set("B1049", "EQ")
sheet.set("A1050", "289037"); sheet.set("B1050", "Arial")
sheet.set("A1051", "289042"); sheet.set("B1051", "SecretInternalRadArrowhead5473618n4")
sheet.set("A1052", "289045"); sheet.set("B1052", "EQ")
sheet.set("A1053", "289048"); sheet.set("B1053", "Arial")
sheet.set("A1054", "289053"); sheet.set("B1054", "SecretInternalTypePreviewgArrowhead5478765182")
sheet.set("A1055", "289056"); sheet.set("B1055", "C:\\pf_root\\dev\\Data\\Platform\\Imperial\\Library\\Annotations\\")
sheet.set("A1056", "289121"); sheet.set("B1056", "Name")
sheet.set("A1057", "289145"); sheet.set("B1057", "Filled Elevation Target Ä")
sheet.set("A1058", "299949"); sheet.set("B1058", "EQ")
sheet.set("A1059", "299952"); sheet.set("B1059", "Arial")
sheet.set("A1060", "299957"); sheet.set("B1060", "SecretInternalLinAngArrowhead54736k182")
sheet.set("A1061", "299960"); sheet.set("B1061", "EQ")
sheet.set("A1062", "299963"); sheet.set("B1062", "Arial")
sheet.set("A1063", "299968"); sheet.set("B1063", "SecretInternalRadArrowhead5473s6187")
sheet.set("A1064", "299971"); sheet.set("B1064", "EQ")
sheet.set("A1065", "299974"); sheet.set("B1065", "Arial")
sheet.set("A1066", "299979"); sheet.set("B1066", "SecretInternalTypePreviewgArrowhead5478765182")
sheet.set("A1067", "299982"); sheet.set("B1067", "C:\\Documents and Settings\\All Users\\Application Data\\Autodesk\\RAC 2009\\Imperial Library\\Detail Components\\Structural\\Concrete\\")
sheet.set("A1068", "299997"); sheet.set("B1068", "Center (Front/Back)")
sheet.set("A1069", "299999"); sheet.set("B1069", "Center (Left/Right)")
sheet.set("A1070", "300042"); sheet.set("B1070", "Bar Diameter")
sheet.set("A1071", "300056"); sheet.set("B1071", "Reinforcing Steel")
sheet.set("A1072", "300066"); sheet.set("B1072", "L1")
sheet.set("A1073", "300070"); sheet.set("B1073", "Revealy")
sheet.set("A1074", "300410"); sheet.set("B1074", "EQ")
sheet.set("A1075", "300413"); sheet.set("B1075", "Arial")
sheet.set("A1076", "300418"); sheet.set("B1076", "SecretInternalLinAngArrowhead54736k182")
sheet.set("A1077", "300421"); sheet.set("B1077", "EQ")
sheet.set("A1078", "300424"); sheet.set("B1078", "Arial")
sheet.set("A1079", "300429"); sheet.set("B1079", "SecretInternalRadArrowhead5473s6187")
sheet.set("A1080", "300432"); sheet.set("B1080", "EQ")
sheet.set("A1081", "300435"); sheet.set("B1081", "Arial")
sheet.set("A1082", "300440"); sheet.set("B1082", "SecretInternalTypePreviewgArrowhead5478765182")
sheet.set("A1083", "300443"); sheet.set("B1083", "C:\\pf_root\\9.0\\Data\\Platform\\Imperial\\Library\\Annotations\\")
sheet.set("A1084", "300457"); sheet.set("B1084", "EQ")
sheet.set("A1085", "129"); sheet.set("B1085", "ry_base.fbx")
sheet.set("A1086", "300421"); sheet.set("B1086", "?r")
sheet.set("A1087", "4294967295"); sheet.set("B1087", "as")
sheet.set("A1088", "0"); sheet.set("B1088", "as")
sheet.set("A1089", "300457"); sheet.set("B1089", "Li")
sheet.set("A1090", "300457"); sheet.set("B1090", "Li")
sheet.set("A1091", "300457"); sheet.set("B1091", "Li")
sheet.set("A1092", "791621423"); sheet.set("B1092", "Li")
sheet.set("A1093", "308957"); sheet.set("B1093", "EQ")
sheet.set("A1094", "308960"); sheet.set("B1094", "Arial")
sheet.set("A1095", "308965"); sheet.set("B1095", "SecretInternalLinAngArrowhead547r36186")
sheet.set("A1096", "308968"); sheet.set("B1096", "EQ")
sheet.set("A1097", "308971"); sheet.set("B1097", "Arial")
sheet.set("A1098", "308976"); sheet.set("B1098", "SecretInternalRadArrowhead5473s6187")
sheet.set("A1099", "308979"); sheet.set("B1099", "EQ")
sheet.set("A1100", "308982"); sheet.set("B1100", "Arial")
sheet.set("A1101", "308987"); sheet.set("B1101", "SecretInternalTypePreviewgArrowhead5478765182")
sheet.set("A1102", "308990"); sheet.set("B1102", "C:\\Documents and Settings\\All Users\\Application Data\\Autodesk\\RAC 2009\\Metric Library\\Doors\\")
sheet.set("A1103", "309000"); sheet.set("B1103", "Ground floor")
sheet.set("A1104", "309009"); sheet.set("B1104", "Wall 1")
sheet.set("A1105", "309010"); sheet.set("B1105", "ÿ5")
sheet.set("A1106", "309038"); sheet.set("B1106", "ÿW")
sheet.set("A1107", "309064"); sheet.set("B1107", "View 1")
sheet.set("A1108", "309092"); sheet.set("B1108", "ÿ2")
sheet.set("A1109", "309137"); sheet.set("B1109", "ÿ\"")
sheet.set("A1110", "309161"); sheet.set("B1110", "ÿ\"")
sheet.set("A1111", "309197"); sheet.set("B1111", "Trim Projection")
sheet.set("A1112", "309228"); sheet.set("B1112", "Stile Width - Latch")
sheet.set("A1113", "309246"); sheet.set("B1113", "Arial")
sheet.set("A1114", "309316"); sheet.set("B1114", "EQ")
sheet.set("A1115", "309337"); sheet.set("B1115", "Level Head - Upgrade")
sheet.set("A1116", "309350"); sheet.set("B1116", "Elevation 1")
sheet.set("A1117", "309395"); sheet.set("B1117", "Name")
sheet.set("A1118", "294704"); sheet.set("B1118", "EQ")
sheet.set("A1119", "294707"); sheet.set("B1119", "Arial")
sheet.set("A1120", "294712"); sheet.set("B1120", "SecretInternalLinAngArrowhead54736k182")
sheet.set("A1121", "294715"); sheet.set("B1121", "EQ")
sheet.set("A1122", "294718"); sheet.set("B1122", "Arial")
sheet.set("A1123", "294723"); sheet.set("B1123", "SecretInternalRadArrowhead5473618n4")
sheet.set("A1124", "294726"); sheet.set("B1124", "EQ")
sheet.set("A1125", "294729"); sheet.set("B1125", "Arial")
sheet.set("A1126", "294734"); sheet.set("B1126", "SecretInternalTypePreviewgArrowhead5478765182")
sheet.set("A1127", "294784"); sheet.set("B1127", "Solid Black")
sheet.set("A1128", "294825"); sheet.set("B1128", "all")
sheet.set("A1129", "289224"); sheet.set("B1129", "EQ")
sheet.set("A1130", "289227"); sheet.set("B1130", "Arial")
sheet.set("A1131", "289232"); sheet.set("B1131", "SecretInternalLinAngArrowhead547r36186")
sheet.set("A1132", "289235"); sheet.set("B1132", "EQ")
sheet.set("A1133", "289238"); sheet.set("B1133", "Arial")
sheet.set("A1134", "289243"); sheet.set("B1134", "SecretInternalRadArrowhead5473618n4")
sheet.set("A1135", "289246"); sheet.set("B1135", "EQ")
sheet.set("A1136", "289249"); sheet.set("B1136", "Arial")
sheet.set("A1137", "289254"); sheet.set("B1137", "SecretInternalTypePreviewgArrowhead5478765182")
sheet.set("A1138", "289257"); sheet.set("B1138", "C:\\pf_root\\9.0\\Data\\Platform\\Imperial\\Library\\Profiles\\Stairs\\")
sheet.set("A1139", "289322"); sheet.set("B1139", "Revealy")
sheet.set("A1140", "310766"); sheet.set("B1140", "EQ")
sheet.set("A1141", "310769"); sheet.set("B1141", "Arial")
sheet.set("A1142", "310774"); sheet.set("B1142", "SecretInternalLinAngArrowhead547r36186")
sheet.set("A1143", "310777"); sheet.set("B1143", "EQ")
sheet.set("A1144", "310780"); sheet.set("B1144", "Arial")
sheet.set("A1145", "310785"); sheet.set("B1145", "SecretInternalRadArrowhead5473s6187")
sheet.set("A1146", "310788"); sheet.set("B1146", "EQ")
sheet.set("A1147", "310791"); sheet.set("B1147", "Arial")
sheet.set("A1148", "310796"); sheet.set("B1148", "SecretInternalTypePreviewgArrowhead5478765182")
sheet.set("A1149", "310799"); sheet.set("B1149", "C:\\My Documents\\2010 Revit Architecture\\Tutorials\\")
sheet.set("A1150", "310776"); sheet.set("B1150", "548")
sheet.set("A1151", "310776"); sheet.set("B1151", "54895489759")
sheet.set("A1152", "310776"); sheet.set("B1152", "54895489759")
sheet.set("A1153", "310776"); sheet.set("B1153", "54895489759")
sheet.set("A1154", "310776"); sheet.set("B1154", "54895489759")
sheet.set("A1155", "310776"); sheet.set("B1155", "54895489759")
sheet.set("A1156", "310776"); sheet.set("B1156", "54895489759")
sheet.set("A1157", "310776"); sheet.set("B1157", "548")
sheet.set("A1158", "310776"); sheet.set("B1158", "548975981")
sheet.set("A1159", "310776"); sheet.set("B1159", "548")
sheet.set("A1160", "310776"); sheet.set("B1160", "548975981")
sheet.set("A1161", "2768863224"); sheet.set("B1161", "op")
sheet.set("A1162", "2768863224"); sheet.set("B1162", "548975981")
sheet.set("A1163", "889503224"); sheet.set("B1163", "48975981")
sheet.set("A1164", "2768863224"); sheet.set("B1164", "Ty")
sheet.set("A1165", "310776"); sheet.set("B1165", "54895")
sheet.set("A1166", "310776"); sheet.set("B1166", "54895")
sheet.set("A1167", "310776"); sheet.set("B1167", "54895")
sheet.set("A1168", "2768863224"); sheet.set("B1168", "op")
sheet.set("A1169", "310776"); sheet.set("B1169", "EQ")
sheet.set("A1170", "2768863224"); sheet.set("B1170", "548975981")
sheet.set("A1171", "310776"); sheet.set("B1171", "5489")
sheet.set("A1172", "310776"); sheet.set("B1172", "U9")
sheet.set("A1173", "310776"); sheet.set("B1173", "548975981")
sheet.set("A1174", "310776"); sheet.set("B1174", "548975981")
sheet.set("A1175", "310776"); sheet.set("B1175", "548975981")
sheet.set("A1176", "671278080"); sheet.set("B1176", "548975981")
sheet.set("A1177", "4037312504"); sheet.set("B1177", "rt")
sheet.set("A1178", "889503224"); sheet.set("B1178", "48975981")
sheet.set("A1179", "4037312504"); sheet.set("B1179", "548975981")
sheet.set("A1180", "310776"); sheet.set("B1180", "54895")
sheet.set("A1181", "310776"); sheet.set("B1181", "54895")
sheet.set("A1182", "4037312504"); sheet.set("B1182", "548975981")
sheet.set("A1183", "310776"); sheet.set("B1183", "54897")
sheet.set("A1184", "310776"); sheet.set("B1184", "ÿV")
sheet.set("A1185", "65280"); sheet.set("B1185", "=8")
sheet.set("A1186", "310776"); sheet.set("B1186", "54897")
sheet.set("A1187", "310776"); sheet.set("B1187", "548975981")
sheet.set("A1188", "65280"); sheet.set("B1188", "=8")
sheet.set("A1189", "310776"); sheet.set("B1189", "54897")
sheet.set("A1190", "4278500856"); sheet.set("B1190", "548975981")
sheet.set("A1191", "310776"); sheet.set("B1191", "UT")
sheet.set("A1192", "4278500856"); sheet.set("B1192", "548975981")
sheet.set("A1193", "310776"); sheet.set("B1193", "UT")
sheet.set("A1194", "671278080"); sheet.set("B1194", "=8")
sheet.set("A1195", "671278080"); sheet.set("B1195", "548975981")
sheet.set("A1196", "311133"); sheet.set("B1196", "3/32\" 3/8\"")
sheet.set("A1197", "311239"); sheet.set("B1197", "<@")
sheet.set("A1198", "311261"); sheet.set("B1198", "EQ")
sheet.set("A1199", "293897"); sheet.set("B1199", "EQ")
sheet.set("A1200", "293900"); sheet.set("B1200", "Arial")
sheet.set("A1201", "293905"); sheet.set("B1201", "SecretInternalLinAngArrowhead54736k182")
sheet.set("A1202", "293908"); sheet.set("B1202", "EQ")
sheet.set("A1203", "293911"); sheet.set("B1203", "Arial")
sheet.set("A1204", "293916"); sheet.set("B1204", "SecretInternalRadArrowhead5473618n4")
sheet.set("A1205", "293919"); sheet.set("B1205", "EQ")
sheet.set("A1206", "293922"); sheet.set("B1206", "Arial")
sheet.set("A1207", "293927"); sheet.set("B1207", "SecretInternalTypePreviewgArrowhead5478765182")
sheet.set("A1208", "293930"); sheet.set("B1208", "\\\\manbsdsrv02\\docs\\bsd\\Architectural_Tutorials\\Revit_Architecture_2010_Tutorials\\Metric Datasets\\09 - Refining the Model\\")
sheet.set("A1209", "293996"); sheet.set("B1209", "ÿ$")
sheet.set("A1210", "280829"); sheet.set("B1210", "EQ")
sheet.set("A1211", "280832"); sheet.set("B1211", "Arial")
sheet.set("A1212", "280837"); sheet.set("B1212", "SecretInternalLinAngArrowhead54736k182")
sheet.set("A1213", "280840"); sheet.set("B1213", "EQ")
sheet.set("A1214", "280843"); sheet.set("B1214", "Arial")
sheet.set("A1215", "280848"); sheet.set("B1215", "SecretInternalRadArrowhead5473618n4")
sheet.set("A1216", "280851"); sheet.set("B1216", "EQ")
sheet.set("A1217", "280854"); sheet.set("B1217", "Arial")
sheet.set("A1218", "280859"); sheet.set("B1218", "SecretInternalTypePreviewgArrowhead5478765182")
sheet.set("A1219", "280862"); sheet.set("B1219", "C:\\pf_root\\9.0\\Data\\Platform\\Metric\\Library\\Profiles\\Stairs\\")
sheet.set("A1220", "280928"); sheet.set("B1220", "Revealy")
sheet.set("A1221", "293254"); sheet.set("B1221", "EQ")
sheet.set("A1222", "293257"); sheet.set("B1222", "Arial")
sheet.set("A1223", "293262"); sheet.set("B1223", "SecretInternalLinAngArrowhead547r36186")
sheet.set("A1224", "293265"); sheet.set("B1224", "EQ")
sheet.set("A1225", "293268"); sheet.set("B1225", "Arial")
sheet.set("A1226", "293273"); sheet.set("B1226", "SecretInternalRadArrowhead5473s6187")
sheet.set("A1227", "293276"); sheet.set("B1227", "EQ")
sheet.set("A1228", "293279"); sheet.set("B1228", "Arial")
sheet.set("A1229", "293284"); sheet.set("B1229", "SecretInternalTypePreviewgArrowhead5478765182")
sheet.set("A1230", "293287"); sheet.set("B1230", "C:\\Documents and Settings\\All Users\\Application Data\\Autodesk\\RAC 2009\\Metric Library\\Doors\\")
sheet.set("A1231", "293297"); sheet.set("B1231", "Base Line")
sheet.set("A1232", "293322"); sheet.set("B1232", "Center (Front/Back")
sheet.set("A1233", "293324"); sheet.set("B1233", "Center (Left/Right)")
sheet.set("A1234", "293325"); sheet.set("B1234", "Left")
sheet.set("A1235", "293326"); sheet.set("B1235", "Right")
sheet.set("A1236", "293327"); sheet.set("B1236", "ðÀ")
sheet.set("A1237", "293330"); sheet.set("B1237", "Top")
sheet.set("A1238", "293339"); sheet.set("B1238", "View 1")
sheet.set("A1239", "293384"); sheet.set("B1239", "ÿl")
sheet.set("A1240", "293397"); sheet.set("B1240", "Section Head - Min")
sheet.set("A1241", "293410"); sheet.set("B1241", "Elevation 1")
sheet.set("A1242", "293466"); sheet.set("B1242", "Section Head - Min")
sheet.set("A1243", "293468"); sheet.set("B1243", "Section Head - Min")
sheet.set("A1244", "293536"); sheet.set("B1244", "ÿb")
sheet.set("A1245", "293586"); sheet.set("B1245", "Glazing Material")
sheet.set("A1246", "278045"); sheet.set("B1246", "EQ")
sheet.set("A1247", "278048"); sheet.set("B1247", "Arial")
sheet.set("A1248", "278053"); sheet.set("B1248", "SecretInternalLinAngArrowhead54736k182")
sheet.set("A1249", "278056"); sheet.set("B1249", "EQ")
sheet.set("A1250", "278059"); sheet.set("B1250", "Arial")
sheet.set("A1251", "278064"); sheet.set("B1251", "SecretInternalRadArrowhead5473618n4")
sheet.set("A1252", "278067"); sheet.set("B1252", "EQ")
sheet.set("A1253", "278070"); sheet.set("B1253", "Arial")
sheet.set("A1254", "278075"); sheet.set("B1254", "SecretInternalTypePreviewgArrowhead5478765182")
sheet.set("A1255", "278078"); sheet.set("B1255", "C:\\pf_root\\9.0\\Data\\Platform\\Metric\\Library\\Annotations\\")
sheet.set("A1256", "278126"); sheet.set("B1256", "Solid Black")
sheet.set("A1257", "278161"); sheet.set("B1257", "all")
sheet.set("A1258", "278184"); sheet.set("B1258", "Elevation 1")
sheet.set("A1259", "294207"); sheet.set("B1259", "EQ")
sheet.set("A1260", "294210"); sheet.set("B1260", "Arial")
sheet.set("A1261", "294215"); sheet.set("B1261", "SecretInternalLinAngArrowhead547r36186")
sheet.set("A1262", "294218"); sheet.set("B1262", "EQ")
sheet.set("A1263", "294221"); sheet.set("B1263", "Arial")
sheet.set("A1264", "294226"); sheet.set("B1264", "SecretInternalRadArrowhead5473s6187")
sheet.set("A1265", "294229"); sheet.set("B1265", "EQ")
sheet.set("A1266", "294232"); sheet.set("B1266", "Arial")
sheet.set("A1267", "294237"); sheet.set("B1267", "SecretInternalTypePreviewgArrowhead5478765182")
sheet.set("A1268", "294240"); sheet.set("B1268", "C:\\Documents and Settings\\All Users\\Application Data\\Autodesk\\RAC 2009\\Metric Library\\Doors\\")
sheet.set("A1269", "294250"); sheet.set("B1269", "Base Line")
sheet.set("A1270", "294220"); sheet.set("B1270", "ac")
sheet.set("A1271", "294220"); sheet.set("B1271", "ac")
sheet.set("A1272", "294220"); sheet.set("B1272", "Base Line")
sheet.set("A1273", "294504"); sheet.set("B1273", "Filled Elevation Target Ä")
sheet.set("A1274", "294510"); sheet.set("B1274", "6.35 mm")
sheet.set("A1275", "309541"); sheet.set("B1275", "EQ")
sheet.set("A1276", "309544"); sheet.set("B1276", "Arial")
sheet.set("A1277", "309549"); sheet.set("B1277", "SecretInternalLinAngArrowhead547r36186")
sheet.set("A1278", "309552"); sheet.set("B1278", "EQ")
sheet.set("A1279", "309555"); sheet.set("B1279", "Arial")
sheet.set("A1280", "309560"); sheet.set("B1280", "SecretInternalRadArrowhead5473s6187")
sheet.set("A1281", "309563"); sheet.set("B1281", "EQ")
sheet.set("A1282", "309566"); sheet.set("B1282", "Arial")
sheet.set("A1283", "309571"); sheet.set("B1283", "SecretInternalTypePreviewgArrowhead5478765182")
sheet.set("A1284", "309574"); sheet.set("B1284", "C:\\Documents and Settings\\All Users\\Application Data\\Autodesk\\RAC 2009\\Imperial Library\\Lighting Fixtures\\")
sheet.set("A1285", "309584"); sheet.set("B1285", "Ref. Level")
sheet.set("A1286", "309609"); sheet.set("B1286", "Light Source Axis")
sheet.set("A1287", "309610"); sheet.set("B1287", "Ceiling")
sheet.set("A1288", "309611"); sheet.set("B1288", "Light Source Axis")
sheet.set("A1289", "309619"); sheet.set("B1289", "Ceiling 1")
sheet.set("A1290", "309643"); sheet.set("B1290", "View 1")
sheet.set("A1291", "309648"); sheet.set("B1291", "Light Source Elevation")
sheet.set("A1292", "309624"); sheet.set("B1292", "enersuenersuenersuenersuenersuener")
sheet.set("A1293", "309624"); sheet.set("B1293", "enersuenersuenersuenersuenersuener")
sheet.set("A1294", "309780"); sheet.set("B1294", "ÿ@")
sheet.set("A1295", "309817"); sheet.set("B1295", "Ceiling 1")
sheet.set("A1296", "309835"); sheet.set("B1296", "Level Head - Upgrade")
sheet.set("A1297", "309848"); sheet.set("B1297", "Elevation 1")
sheet.set("A1298", "309893"); sheet.set("B1298", "Name")
sheet.set("A1299", "309918"); sheet.set("B1299", "Filled Elevation Target Ä")
sheet.set("A1300", "309924"); sheet.set("B1300", "1/4\"")
sheet.set("A1301", "309993"); sheet.set("B1301", "ÿ\"")
sheet.set("A1302", "309997"); sheet.set("B1302", "{3D}")
sheet.set("A1303", "301217"); sheet.set("B1303", "EQ")
sheet.set("A1304", "301220"); sheet.set("B1304", "Arial")
sheet.set("A1305", "301225"); sheet.set("B1305", "SecretInternalLinAngArrowhead54736k182")
sheet.set("A1306", "301228"); sheet.set("B1306", "EQ")
sheet.set("A1307", "301231"); sheet.set("B1307", "Arial")
sheet.set("A1308", "301236"); sheet.set("B1308", "SecretInternalRadArrowhead5473618n4")
sheet.set("A1309", "301239"); sheet.set("B1309", "EQ")
sheet.set("A1310", "301242"); sheet.set("B1310", "Arial")
sheet.set("A1311", "301247"); sheet.set("B1311", "SecretInternalTypePreviewgArrowhead5478765182")
sheet.set("A1312", "301250"); sheet.set("B1312", "C:\\pf_root\\9.0\\Data\\Platform\\Imperial\\Library\\Annotations\\")
sheet.set("A1313", "301298"); sheet.set("B1313", "A101")
sheet.set("A1314", "301313"); sheet.set("B1314", "Revealy")
sheet.set("A1315", "276887"); sheet.set("B1315", "EQ")
sheet.set("A1316", "276890"); sheet.set("B1316", "Arial")
sheet.set("A1317", "276895"); sheet.set("B1317", "SecretInternalLinAngArrowhead547r36186")
sheet.set("A1318", "276898"); sheet.set("B1318", "EQ")
sheet.set("A1319", "276901"); sheet.set("B1319", "Arial")
sheet.set("A1320", "276906"); sheet.set("B1320", "SecretInternalRadArrowhead5473618n4")
sheet.set("A1321", "276909"); sheet.set("B1321", "EQ")
sheet.set("A1322", "276912"); sheet.set("B1322", "Arial")
sheet.set("A1323", "276917"); sheet.set("B1323", "SecretInternalTypePreviewgArrowhead5478765182")
sheet.set("A1324", "276920"); sheet.set("B1324", "C:\\pf_root\\dev\\Data\\Platform\\Metric\\Library\\Annotations\\")
sheet.set("A1325", "276985"); sheet.set("B1325", "Name")
sheet.set("A1326", "277008"); sheet.set("B1326", "Filled Elevation Target Ä")
sheet.set("A1327", "277013"); sheet.set("B1327", "allw")
sheet.set("A1328", "296875"); sheet.set("B1328", "EQ")
sheet.set("A1329", "296878"); sheet.set("B1329", "Arial")
sheet.set("A1330", "296883"); sheet.set("B1330", "SecretInternalLinAngArrowhead54736k182")
sheet.set("A1331", "296886"); sheet.set("B1331", "EQ")
sheet.set("A1332", "296889"); sheet.set("B1332", "Arial")
sheet.set("A1333", "296894"); sheet.set("B1333", "SecretInternalRadArrowhead5473618n4")
sheet.set("A1334", "296897"); sheet.set("B1334", "EQ")
sheet.set("A1335", "296900"); sheet.set("B1335", "Arial")
sheet.set("A1336", "296905"); sheet.set("B1336", "SecretInternalTypePreviewgArrowhead5478765182")
sheet.set("A1337", "296971"); sheet.set("B1337", "Center (Front/Back)")
sheet.set("A1338", "296973"); sheet.set("B1338", "Center (Left/Right)")
sheet.set("A1339", "297054"); sheet.set("B1339", "Width")
sheet.set("A1340", "297059"); sheet.set("B1340", "ÿl")
sheet.set("A1341", "297215"); sheet.set("B1341", "EQ")
sheet.set("A1342", "297218"); sheet.set("B1342", "Arial")
sheet.set("A1343", "297223"); sheet.set("B1343", "SecretInternalLinAngArrowhead547r36186")
sheet.set("A1344", "297226"); sheet.set("B1344", "EQ")
sheet.set("A1345", "297229"); sheet.set("B1345", "Arial")
sheet.set("A1346", "297234"); sheet.set("B1346", "SecretInternalRadArrowhead5473s6187")
sheet.set("A1347", "297237"); sheet.set("B1347", "EQ")
sheet.set("A1348", "297240"); sheet.set("B1348", "Arial")
sheet.set("A1349", "297245"); sheet.set("B1349", "SecretInternalTypePreviewgArrowhead5478765182")
sheet.set("A1350", "297287"); sheet.set("B1350", "Center (Front/Back)")
sheet.set("A1351", "297289"); sheet.set("B1351", "Center (Left/Right)")
sheet.set("A1352", "297340"); sheet.set("B1352", "View 1")
sheet.set("A1353", "297363"); sheet.set("B1353", "Section Head - Min")
sheet.set("A1354", "297376"); sheet.set("B1354", "Elevation 1")
sheet.set("A1355", "297432"); sheet.set("B1355", "Section Head - Min")
sheet.set("A1356", "297434"); sheet.set("B1356", "Section Head - Min")
sheet.set("A1357", "297456"); sheet.set("B1357", "Level Head - Upgrade")
sheet.set("A1358", "297469"); sheet.set("B1358", "Elevation 1")
sheet.set("A1359", "297514"); sheet.set("B1359", "Name")
sheet.set("A1360", "297519"); sheet.set("B1360", "ial")
sheet.set("A1361", "297522"); sheet.set("B1361", "ial")
sheet.set("A1362", "297580"); sheet.set("B1362", "3/16\" 1/2\"")
sheet.set("A1363", "297582"); sheet.set("B1363", "3/32\" 3/8\"")
sheet.set("A1364", "297584"); sheet.set("B1364", "S@")
sheet.set("A1365", "297601"); sheet.set("B1365", "Elevation 1")
sheet.set("A1366", "297693"); sheet.set("B1366", "ÿ6")
sheet.set("A1367", "297695"); sheet.set("B1367", "Profile plane")
sheet.set("A1368", "297714"); sheet.set("B1368", "Profile plane")
sheet.set("A1369", "297721"); sheet.set("B1369", "Arial")
sheet.set("A1370", "297731"); sheet.set("B1370", "ÿ>")
sheet.set("A1371", "297732"); sheet.set("B1371", "ÿ6")
sheet.set("A1372", "297734"); sheet.set("B1372", "Profile plane")
sheet.set("A1373", "297741"); sheet.set("B1373", "Arial")
sheet.set("A1374", "297753"); sheet.set("B1374", "Profile plane")
sheet.set("A1375", "297760"); sheet.set("B1375", "Arial")
sheet.set("A1376", "297761"); sheet.set("B1376", "Arial")
sheet.set("A1377", "297769"); sheet.set("B1377", "Rebar Cover 1}")
sheet.set("A1378", "277858"); sheet.set("B1378", "EQ")
sheet.set("A1379", "277861"); sheet.set("B1379", "Arial")
sheet.set("A1380", "277866"); sheet.set("B1380", "SecretInternalLinAngArrowhead54736k182")
sheet.set("A1381", "277869"); sheet.set("B1381", "EQ")
sheet.set("A1382", "277872"); sheet.set("B1382", "Arial")
sheet.set("A1383", "277877"); sheet.set("B1383", "SecretInternalRadArrowhead5473618n4")
sheet.set("A1384", "277880"); sheet.set("B1384", "EQ")
sheet.set("A1385", "277883"); sheet.set("B1385", "Arial")
sheet.set("A1386", "277888"); sheet.set("B1386", "SecretInternalTypePreviewgArrowhead5478765182")
sheet.set("A1387", "277891"); sheet.set("B1387", "C:\\pf_root\\9.0\\Data\\Platform\\Metric\\Library\\Annotations\\")
sheet.set("A1388", "277904"); sheet.set("B1388", "Baseline")
sheet.set("A1389", "277940"); sheet.set("B1389", "A101")
sheet.set("A1390", "277950"); sheet.set("B1390", "Ref")
sheet.set("A1391", "280237"); sheet.set("B1391", "EQ")
sheet.set("A1392", "280240"); sheet.set("B1392", "Arial")
sheet.set("A1393", "280245"); sheet.set("B1393", "SecretInternalLinAngArrowhead547r36186")
sheet.set("A1394", "280248"); sheet.set("B1394", "EQ")
sheet.set("A1395", "280251"); sheet.set("B1395", "Arial")
sheet.set("A1396", "280256"); sheet.set("B1396", "SecretInternalRadArrowhead5473s6187")
sheet.set("A1397", "280259"); sheet.set("B1397", "EQ")
sheet.set("A1398", "280262"); sheet.set("B1398", "Arial")
sheet.set("A1399", "280267"); sheet.set("B1399", "SecretInternalTypePreviewgArrowhead5478765182")
sheet.set("A1400", "280270"); sheet.set("B1400", "C:\\pf_root\\9.0\\Data\\Platform\\Metric\\Library\\Site\\Parking\\")
sheet.set("A1401", "280251"); sheet.set("B1401", "crl")
sheet.set("A1402", "280251"); sheet.set("B1402", "efault ")
sheet.set("A1403", "1566399931"); sheet.set("B1403", "efault l")
sheet.set("A1404", "280251"); sheet.set("B1404", "efault ")
sheet.set("A1405", "280251"); sheet.set("B1405", "efault ")
sheet.set("A1406", "2605109435"); sheet.set("B1406", "efault ")
sheet.set("A1407", "2605109435"); sheet.set("B1407", "1 : ")
sheet.set("A1408", "2605109435"); sheet.set("B1408", "]a")
sheet.set("A1409", "2605109435"); sheet.set("B1409", "Bl")
sheet.set("A1410", "2605109435"); sheet.set("B1410", "me")
sheet.set("A1411", "2605109435"); sheet.set("B1411", "G.")
sheet.set("A1412", "281257"); sheet.set("B1412", "EQ")
sheet.set("A1413", "281260"); sheet.set("B1413", "Arial")
sheet.set("A1414", "281265"); sheet.set("B1414", "SecretInternalLinAngArrowhead547r36186")
sheet.set("A1415", "281268"); sheet.set("B1415", "EQ")
sheet.set("A1416", "281271"); sheet.set("B1416", "Arial")
sheet.set("A1417", "281276"); sheet.set("B1417", "SecretInternalRadArrowhead5473618n4")
sheet.set("A1418", "281279"); sheet.set("B1418", "EQ")
sheet.set("A1419", "281282"); sheet.set("B1419", "Arial")
sheet.set("A1420", "281287"); sheet.set("B1420", "SecretInternalTypePreviewgArrowhead5478765182")
sheet.set("A1421", "281290"); sheet.set("B1421", "C:\\pf_root\\9.0\\Data\\Platform\\Metric\\Library\\Profiles\\Roofs\\")
sheet.set("A1422", "281358"); sheet.set("B1422", "ÿC")
sheet.set("A1423", "281379"); sheet.set("B1423", "EQ")
sheet.set("A1424", "303716"); sheet.set("B1424", "EQ")
sheet.set("A1425", "303719"); sheet.set("B1425", "Arial")
sheet.set("A1426", "303724"); sheet.set("B1426", "SecretInternalLinAngArrowhead547r36186")
sheet.set("A1427", "303727"); sheet.set("B1427", "EQ")
sheet.set("A1428", "303730"); sheet.set("B1428", "Arial")
sheet.set("A1429", "303735"); sheet.set("B1429", "SecretInternalRadArrowhead5473s6187")
sheet.set("A1430", "303738"); sheet.set("B1430", "EQ")
sheet.set("A1431", "303741"); sheet.set("B1431", "Arial")
sheet.set("A1432", "303746"); sheet.set("B1432", "SecretInternalTypePreviewgArrowhead5478765182")
sheet.set("A1433", "303749"); sheet.set("B1433", "C:\\Documents and Settings\\All Users\\Application Data\\Autodesk\\RAC 2009\\Imperial Library\\")
sheet.set("A1434", "303786"); sheet.set("B1434", "Center F/B")
sheet.set("A1435", "303788"); sheet.set("B1435", "Center L/R")
sheet.set("A1436", "303988"); sheet.set("B1436", "ÿ!")
sheet.set("A1437", "304008"); sheet.set("B1437", "ÿ|")
sheet.set("A1438", "304010"); sheet.set("B1438", "ÿx")
sheet.set("A1439", "304012"); sheet.set("B1439", "ÿ{")
sheet.set("A1440", "304017"); sheet.set("B1440", "View 1")
sheet.set("A1441", "304036"); sheet.set("B1441", "ÿK")
sheet.set("A1442", "304091"); sheet.set("B1442", "ÿ?")
sheet.set("A1443", "304092"); sheet.set("B1443", "ÿE")
sheet.set("A1444", "304093"); sheet.set("B1444", "ÿ?")
sheet.set("A1445", "304094"); sheet.set("B1445", "ÿ?")
sheet.set("A1446", "304095"); sheet.set("B1446", "ÿI")
sheet.set("A1447", "304114"); sheet.set("B1447", "Profile plane")
sheet.set("A1448", "304124"); sheet.set("B1448", "Filled Elevation Target Ä")
sheet.set("A1449", "304137"); sheet.set("B1449", "Level Head - Upgrade")
sheet.set("A1450", "304150"); sheet.set("B1450", "Elevation 1")
sheet.set("A1451", "304195"); sheet.set("B1451", "Name")
sheet.set("A1452", "304220"); sheet.set("B1452", "Filled Elevation Target Ä")
sheet.set("A1453", "304226"); sheet.set("B1453", "1/4\"")
sheet.set("A1454", "302051"); sheet.set("B1454", "EQ")
sheet.set("A1455", "302054"); sheet.set("B1455", "Arial")
sheet.set("A1456", "302059"); sheet.set("B1456", "SecretInternalLinAngArrowhead54736k182")
sheet.set("A1457", "302062"); sheet.set("B1457", "EQ")
sheet.set("A1458", "302065"); sheet.set("B1458", "Arial")
sheet.set("A1459", "302070"); sheet.set("B1459", "SecretInternalRadArrowhead5473s6187")
sheet.set("A1460", "302073"); sheet.set("B1460", "EQ")
sheet.set("A1461", "302076"); sheet.set("B1461", "Arial")
sheet.set("A1462", "302081"); sheet.set("B1462", "SecretInternalTypePreviewgArrowhead5478765182")
sheet.set("A1463", "302084"); sheet.set("B1463", "C:\\Documents and Settings\\campbes\\Desktop\\")
sheet.set("A1464", "302099"); sheet.set("B1464", "Center (Front/Back)")
sheet.set("A1465", "302101"); sheet.set("B1465", "Center (Left/Right)")
sheet.set("A1466", "302266"); sheet.set("B1466", "Left")
sheet.set("A1467", "302267"); sheet.set("B1467", "Right")
sheet.set("A1468", "302283"); sheet.set("B1468", "Rebar Cover 1}")
sheet.set("A1469", "281042"); sheet.set("B1469", "EQ")
sheet.set("A1470", "281045"); sheet.set("B1470", "Arial")
sheet.set("A1471", "281050"); sheet.set("B1471", "SecretInternalLinAngArrowhead547r36186")
sheet.set("A1472", "281053"); sheet.set("B1472", "EQ")
sheet.set("A1473", "281056"); sheet.set("B1473", "Arial")
sheet.set("A1474", "281061"); sheet.set("B1474", "SecretInternalRadArrowhead5473618n4")
sheet.set("A1475", "281064"); sheet.set("B1475", "EQ")
sheet.set("A1476", "281067"); sheet.set("B1476", "Arial")
sheet.set("A1477", "281072"); sheet.set("B1477", "SecretInternalTypePreviewgArrowhead5478765182")
sheet.set("A1478", "281075"); sheet.set("B1478", "C:\\pf_root\\9.0\\Data\\Platform\\Metric\\Library\\Profiles\\Stairs\\")
sheet.set("A1479", "281140"); sheet.set("B1479", "Revealy")
sheet.set("A1480", "281188"); sheet.set("B1480", "Elevation 1")
sheet.set("A1481", "277088"); sheet.set("B1481", "EQ")
sheet.set("A1482", "277091"); sheet.set("B1482", "Arial")
sheet.set("A1483", "277096"); sheet.set("B1483", "SecretInternalLinAngArrowhead54736k182")
sheet.set("A1484", "277099"); sheet.set("B1484", "EQ")
sheet.set("A1485", "277102"); sheet.set("B1485", "Arial")
sheet.set("A1486", "277107"); sheet.set("B1486", "SecretInternalRadArrowhead5473618n4")
sheet.set("A1487", "277110"); sheet.set("B1487", "EQ")
sheet.set("A1488", "277113"); sheet.set("B1488", "Arial")
sheet.set("A1489", "277118"); sheet.set("B1489", "SecretInternalTypePreviewgArrowhead5478765182")
sheet.set("A1490", "277121"); sheet.set("B1490", "C:\\pf_root\\dev\\Data\\Platform\\Metric\\Library\\Annotations\\")
sheet.set("A1491", "277154"); sheet.set("B1491", "Arial")
sheet.set("A1492", "279201"); sheet.set("B1492", "EQ")
sheet.set("A1493", "279204"); sheet.set("B1493", "Arial")
sheet.set("A1494", "279209"); sheet.set("B1494", "SecretInternalLinAngArrowhead54736k182")
sheet.set("A1495", "279212"); sheet.set("B1495", "EQ")
sheet.set("A1496", "279215"); sheet.set("B1496", "Arial")
sheet.set("A1497", "279220"); sheet.set("B1497", "SecretInternalRadArrowhead5473s6187")
sheet.set("A1498", "279223"); sheet.set("B1498", "EQ")
sheet.set("A1499", "279226"); sheet.set("B1499", "Arial")
sheet.set("A1500", "279231"); sheet.set("B1500", "SecretInternalTypePreviewgArrowhead5478765182")
sheet.set("A1501", "279234"); sheet.set("B1501", "C:\\pf_root\\9.0\\Data\\Platform\\Metric\\Library\\Annotations\\Architectural\\")
sheet.set("A1502", "279260"); sheet.set("B1502", "Arrowhead 1")
sheet.set("A1503", "282974"); sheet.set("B1503", "EQ")
sheet.set("A1504", "282977"); sheet.set("B1504", "Arial")
sheet.set("A1505", "282982"); sheet.set("B1505", "SecretInternalLinAngArrowhead547r36186")
sheet.set("A1506", "282985"); sheet.set("B1506", "EQ")
sheet.set("A1507", "282988"); sheet.set("B1507", "Arial")
sheet.set("A1508", "282993"); sheet.set("B1508", "SecretInternalRadArrowhead5473s6187")
sheet.set("A1509", "282996"); sheet.set("B1509", "EQ")
sheet.set("A1510", "282999"); sheet.set("B1510", "Arial")
sheet.set("A1511", "283004"); sheet.set("B1511", "SecretInternalTypePreviewgArrowhead5478765182")
sheet.set("A1512", "283007"); sheet.set("B1512", "C:\\pf_root\\9.0\\Data\\Platform\\Metric\\Library\\Structural\\Columns\\Steel\\")
sheet.set("A1513", "283027"); sheet.set("B1513", "Lower Ref. Level")
sheet.set("A1514", "283036"); sheet.set("B1514", "Upper Ref Level")
sheet.set("A1515", "283062"); sheet.set("B1515", "ÿ&")
sheet.set("A1516", "283105"); sheet.set("B1516", "ÿ2")
sheet.set("A1517", "283141"); sheet.set("B1517", "ÿB")
sheet.set("A1518", "283180"); sheet.set("B1518", "{3D}")
sheet.set("A1519", "283244"); sheet.set("B1519", "Level Head - Upgrade")
sheet.set("A1520", "283257"); sheet.set("B1520", "Elevation 1")
sheet.set("A1521", "283302"); sheet.set("B1521", "Name")
sheet.set("A1522", "283327"); sheet.set("B1522", "Filled Elevation Target Ä")
sheet.set("A1523", "283333"); sheet.set("B1523", "6.35 mm")
sheet.set("A1524", "292771"); sheet.set("B1524", "EQ")
sheet.set("A1525", "292774"); sheet.set("B1525", "Arial")
sheet.set("A1526", "292779"); sheet.set("B1526", "SecretInternalLinAngArrowhead547r36186")
sheet.set("A1527", "292782"); sheet.set("B1527", "EQ")
sheet.set("A1528", "292785"); sheet.set("B1528", "Arial")
sheet.set("A1529", "292786"); sheet.set("B1529", "SecretIntern")
sheet.set("A1530", "292785"); sheet.set("B1530", "Arial")
sheet.set("A1531", "4294933742"); sheet.set("B1531", "Arial")
sheet.set("A1532", "292785"); sheet.set("B1532", "Arial")
sheet.set("A1533", "2038004075"); sheet.set("B1533", "StT")
sheet.set("A1534", "2038004075"); sheet.set("B1534", " 1")
sheet.set("A1535", "2038004075"); sheet.set("B1535", "ÿQ")
sheet.set("A1536", "292965"); sheet.set("B1536", "Trim Width Ext.")
sheet.set("A1537", "292970"); sheet.set("B1537", "Arial")
sheet.set("A1538", "293032"); sheet.set("B1538", "Level Head - Upgrade")
sheet.set("A1539", "293045"); sheet.set("B1539", "Elevation 1")
sheet.set("A1540", "293090"); sheet.set("B1540", "Name")
sheet.set("A1541", "293115"); sheet.set("B1541", "Filled Elevation Target Ä")
sheet.set("A1542", "293121"); sheet.set("B1542", "6.35 mm")
sheet.set("A1543", "293144"); sheet.set("B1543", "Elevation")
sheet.set("A1544", "311648"); sheet.set("B1544", "EQ")
sheet.set("A1545", "311651"); sheet.set("B1545", "Arial")
sheet.set("A1546", "311656"); sheet.set("B1546", "SecretInternalLinAngArrowhead547r36186")
sheet.set("A1547", "311659"); sheet.set("B1547", "EQ")
sheet.set("A1548", "311662"); sheet.set("B1548", "Arial")
sheet.set("A1549", "311667"); sheet.set("B1549", "SecretInternalRadArrowhead5473s6187")
sheet.set("A1550", "311670"); sheet.set("B1550", "EQ")
sheet.set("A1551", "311673"); sheet.set("B1551", "Arial")
sheet.set("A1552", "311678"); sheet.set("B1552", "SecretInternalTypePreviewgArrowhead5478765182")
sheet.set("A1553", "311681"); sheet.set("B1553", "C:\\Documents and Settings\\All Users\\Application Data\\Autodesk\\RAC 2009\\Metric Library\\Entourage\\")
sheet.set("A1554", "311716"); sheet.set("B1554", "Center (Front/Back)")
sheet.set("A1555", "311718"); sheet.set("B1555", "Center (Left/Right)")
sheet.set("A1556", "311762"); sheet.set("B1556", "Preview")
sheet.set("A1557", "311770"); sheet.set("B1557", "ÿ(")
sheet.set("A1558", "4294967206"); sheet.set("B1558", "ê ")
sheet.set("A1559", "311770"); sheet.set("B1559", "ib")
sheet.set("A1560", "291796"); sheet.set("B1560", "EQ")
sheet.set("A1561", "291799"); sheet.set("B1561", "Arial")
sheet.set("A1562", "291804"); sheet.set("B1562", "SecretInternalLinAngArrowhead547r36186")
sheet.set("A1563", "291807"); sheet.set("B1563", "EQ")
sheet.set("A1564", "291810"); sheet.set("B1564", "Arial")
sheet.set("A1565", "291815"); sheet.set("B1565", "SecretInternalRadArrowhead5473s6187")
sheet.set("A1566", "291818"); sheet.set("B1566", "EQ")
sheet.set("A1567", "291821"); sheet.set("B1567", "Arial")
sheet.set("A1568", "291826"); sheet.set("B1568", "SecretInternalTypePreviewgArrowhead5478765182")
sheet.set("A1569", "291829"); sheet.set("B1569", "C:\\pf_root\\dev\\Data\\Metric\\Library\\Furniture\\")
sheet.set("A1570", "291866"); sheet.set("B1570", "Center (Front/Back)")
sheet.set("A1571", "291868"); sheet.set("B1571", "Center (Left/Right)")
sheet.set("A1572", "291869"); sheet.set("B1572", "View 1")
sheet.set("A1573", "291891"); sheet.set("B1573", "ÿ6")
sheet.set("A1574", "291892"); sheet.set("B1574", "Profile plane")
sheet.set("A1575", "291903"); sheet.set("B1575", "left")
sheet.set("A1576", "291904"); sheet.set("B1576", "right")
sheet.set("A1577", "291911"); sheet.set("B1577", "ÿP")
sheet.set("A1578", "291912"); sheet.set("B1578", "Profile plane")
sheet.set("A1579", "291925"); sheet.set("B1579", "ÿP")
sheet.set("A1580", "291926"); sheet.set("B1580", "Profile plane")
sheet.set("A1581", "291937"); sheet.set("B1581", "Seat")
sheet.set("A1582", "291940"); sheet.set("B1582", "ÿB")
sheet.set("A1583", "291949"); sheet.set("B1583", "back")
sheet.set("A1584", "291952"); sheet.set("B1584", "ÿ\"")
sheet.set("A1585", "291960"); sheet.set("B1585", "Arial")
sheet.set("A1586", "291979"); sheet.set("B1586", "Revealy")
sheet.set("A1587", "292024"); sheet.set("B1587", "Level Head - Upgrade")
sheet.set("A1588", "292037"); sheet.set("B1588", "Elevation 1")
sheet.set("A1589", "292082"); sheet.set("B1589", "Name")
sheet.set("A1590", "292107"); sheet.set("B1590", "Filled Elevation Target Ä")
sheet.set("A1591", "292113"); sheet.set("B1591", "6.35 mm")
sheet.set("A1592", "292222"); sheet.set("B1592", "EQ")
sheet.set("A1593", "285291"); sheet.set("B1593", "EQ")
sheet.set("A1594", "285294"); sheet.set("B1594", "Arial")
sheet.set("A1595", "285299"); sheet.set("B1595", "SecretInternalLinAngArrowhead54736k182")
sheet.set("A1596", "285302"); sheet.set("B1596", "EQ")
sheet.set("A1597", "285305"); sheet.set("B1597", "Arial")
sheet.set("A1598", "285310"); sheet.set("B1598", "SecretInternalRadArrowhead5473s6187")
sheet.set("A1599", "285313"); sheet.set("B1599", "EQ")
sheet.set("A1600", "285316"); sheet.set("B1600", "Arial")
sheet.set("A1601", "285321"); sheet.set("B1601", "SecretInternalTypePreviewgArrowhead5478765182")
sheet.set("A1602", "285324"); sheet.set("B1602", "F:\\pf_root\\dev\\Data\\Platform\\Metric\\Library\\Annotations\\")
sheet.set("A1603", "285382"); sheet.set("B1603", "Date")
sheet.set("A1604", "294850"); sheet.set("B1604", "EQ")
sheet.set("A1605", "294853"); sheet.set("B1605", "Arial")
sheet.set("A1606", "294858"); sheet.set("B1606", "SecretInternalLinAngArrowhead547r36186")
sheet.set("A1607", "294861"); sheet.set("B1607", "EQ")
sheet.set("A1608", "294864"); sheet.set("B1608", "Arial")
sheet.set("A1609", "294869"); sheet.set("B1609", "SecretInternalRadArrowhead5473s6187")
sheet.set("A1610", "294872"); sheet.set("B1610", "EQ")
sheet.set("A1611", "294875"); sheet.set("B1611", "Arial")
sheet.set("A1612", "294880"); sheet.set("B1612", "SecretInternalTypePreviewgArrowhead5478765182")
sheet.set("A1613", "294896"); sheet.set("B1613", "Ref. Level")
sheet.set("A1614", "294921"); sheet.set("B1614", "Center (Front/Back)")
sheet.set("A1615", "294923"); sheet.set("B1615", "Center (Left/Right)")
sheet.set("A1616", "294974"); sheet.set("B1616", "View 1")
sheet.set("A1617", "294984"); sheet.set("B1617", "ÿl")
sheet.set("A1618", "294996"); sheet.set("B1618", "Section Head - Min")
sheet.set("A1619", "295009"); sheet.set("B1619", "Elevation 1")
sheet.set("A1620", "295065"); sheet.set("B1620", "Section Head - Min")
sheet.set("A1621", "295067"); sheet.set("B1621", "Section Head - Min")
sheet.set("A1622", "153"); sheet.set("B1622", " -")
sheet.set("A1623", "295009"); sheet.set("B1623", "Su")
sheet.set("A1624", "295063"); sheet.set("B1624", "B\"")
sheet.set("A1625", "295065"); sheet.set("B1625", " -")
sheet.set("A1626", "295065"); sheet.set("B1626", " -")
sheet.set("A1627", "295063"); sheet.set("B1627", " -")
sheet.set("A1628", "295063"); sheet.set("B1628", " -")
sheet.set("A1629", "295065"); sheet.set("B1629", " -")
sheet.set("A1630", "295065"); sheet.set("B1630", " -")
sheet.set("A1631", "295063"); sheet.set("B1631", " -")
sheet.set("A1632", "295065"); sheet.set("B1632", " -")
sheet.set("A1633", "295063"); sheet.set("B1633", " -")
sheet.set("A1634", "295063"); sheet.set("B1634", "ÿ -")
sheet.set("A1635", "295065"); sheet.set("B1635", " -")
sheet.set("A1636", "295065"); sheet.set("B1636", " -")
sheet.set("A1637", "295065"); sheet.set("B1637", " -")
sheet.set("A1638", "295063"); sheet.set("B1638", " -")
sheet.set("A1639", "295065"); sheet.set("B1639", " -")
sheet.set("A1640", "295215"); sheet.set("B1640", "3/32\" 3/8\"")
sheet.set("A1641", "295312"); sheet.set("B1641", "{3D}")
sheet.set("A1642", "295320"); sheet.set("B1642", "ÿb")
sheet.set("A1643", "307034"); sheet.set("B1643", "EQ")
sheet.set("A1644", "307037"); sheet.set("B1644", "Arial")
sheet.set("A1645", "307042"); sheet.set("B1645", "SecretInternalLinAngArrowhead547r36186")
sheet.set("A1646", "307045"); sheet.set("B1646", "EQ")
sheet.set("A1647", "307048"); sheet.set("B1647", "Arial")
sheet.set("A1648", "307053"); sheet.set("B1648", "SecretInternalRadArrowhead5473s6187")
sheet.set("A1649", "307056"); sheet.set("B1649", "EQ")
sheet.set("A1650", "307059"); sheet.set("B1650", "Arial")
sheet.set("A1651", "307064"); sheet.set("B1651", "SecretInternalTypePreviewgArrowhead5478765182")
sheet.set("A1652", "307067"); sheet.set("B1652", "C:\\Documents and Settings\\All Users\\Application Data\\Autodesk\\RAC 2009\\Imperial Library\\")
sheet.set("A1653", "307102"); sheet.set("B1653", "Center F/B")
sheet.set("A1654", "307104"); sheet.set("B1654", "Center L/R")
sheet.set("A1655", "307144"); sheet.set("B1655", "ÙÀ")
sheet.set("A1656", "307149"); sheet.set("B1656", "ÿ&")
sheet.set("A1657", "307157"); sheet.set("B1657", "ÿ&")
sheet.set("A1658", "307158"); sheet.set("B1658", "ÿj")
sheet.set("A1659", "307163"); sheet.set("B1659", "View 1")
sheet.set("A1660", "307221"); sheet.set("B1660", "Level Head - Upgrade")
sheet.set("A1661", "307169"); sheet.set("B1661", "Ti")
sheet.set("A1662", "303450"); sheet.set("B1662", "EQ")
sheet.set("A1663", "303453"); sheet.set("B1663", "Arial")
sheet.set("A1664", "303458"); sheet.set("B1664", "SecretInternalLinAngArrowhead54736k182")
sheet.set("A1665", "303461"); sheet.set("B1665", "EQ")
sheet.set("A1666", "303464"); sheet.set("B1666", "Arial")
sheet.set("A1667", "303469"); sheet.set("B1667", "SecretInternalRadArrowhead5473s6187")
sheet.set("A1668", "303472"); sheet.set("B1668", "EQ")
sheet.set("A1669", "303475"); sheet.set("B1669", "Arial")
sheet.set("A1670", "303480"); sheet.set("B1670", "SecretInternalTypePreviewgArrowhead5478765182")
sheet.set("A1671", "303483"); sheet.set("B1671", "C:\\Documents and Settings\\All Users\\Application Data\\Autodesk\\RAC 2009\\Metric Library\\Detail Components\\Div 07-Thermal and Moisture Protection\\07200-Thermal Protection\\07210-Building Insulation\\")
sheet.set("A1672", "303498"); sheet.set("B1672", "Center (Front/Back)")
sheet.set("A1673", "303500"); sheet.set("B1673", "Left")
sheet.set("A1674", "303543"); sheet.set("B1674", "Wood - Finish")
sheet.set("A1675", "303670"); sheet.set("B1675", "Right")
sheet.set("A1676", "303672"); sheet.set("B1676", "Thickness")
sheet.set("A1677", "303686"); sheet.set("B1677", "Plywood")
sheet.set("A1678", "312008"); sheet.set("B1678", "EQ")
sheet.set("A1679", "312011"); sheet.set("B1679", "Arial")
sheet.set("A1680", "312016"); sheet.set("B1680", "SecretInternalLinAngArrowhead547r36186")
sheet.set("A1681", "312019"); sheet.set("B1681", "EQ")
sheet.set("A1682", "312022"); sheet.set("B1682", "Arial")
sheet.set("A1683", "312027"); sheet.set("B1683", "SecretInternalRadArrowhead5473s6187")
sheet.set("A1684", "312030"); sheet.set("B1684", "EQ")
sheet.set("A1685", "312033"); sheet.set("B1685", "Arial")
sheet.set("A1686", "312038"); sheet.set("B1686", "SecretInternalTypePreviewgArrowhead5478765182")
sheet.set("A1687", "312041"); sheet.set("B1687", "C:\\Documents and Settings\\egberte\\Desktop\\Projects\\elev tags\\content\\")
sheet.set("A1688", "312242"); sheet.set("B1688", "Ref")
sheet.set("A1689", "312243"); sheet.set("B1689", "Ref")
sheet.set("A1690", "312244"); sheet.set("B1690", "Ref")
sheet.set("A1691", "312245"); sheet.set("B1691", "View Name")
sheet.set("A1692", "312246"); sheet.set("B1692", "View Name")
sheet.set("A1693", "312247"); sheet.set("B1693", "View Name")
sheet.set("A1694", "278441"); sheet.set("B1694", "EQ")
sheet.set("A1695", "278444"); sheet.set("B1695", "Arial")
sheet.set("A1696", "278449"); sheet.set("B1696", "SecretInternalLinAngArrowhead54736k182")
sheet.set("A1697", "278452"); sheet.set("B1697", "EQ")
sheet.set("A1698", "278455"); sheet.set("B1698", "Arial")
sheet.set("A1699", "278460"); sheet.set("B1699", "SecretInternalRadArrowhead5473s6187")
sheet.set("A1700", "278463"); sheet.set("B1700", "EQ")
sheet.set("A1701", "278466"); sheet.set("B1701", "Arial")
sheet.set("A1702", "278471"); sheet.set("B1702", "SecretInternalTypePreviewgArrowhead5478765182")
sheet.set("A1703", "278474"); sheet.set("B1703", "C:\\pf_root\\9.0\\Data\\Platform\\Metric\\Library\\Annotations\\")
sheet.set("A1704", "278552"); sheet.set("B1704", "Filled Elevation Target Ä")
sheet.set("A1705", "281935"); sheet.set("B1705", "EQ")
sheet.set("A1706", "281938"); sheet.set("B1706", "Arial")
sheet.set("A1707", "281943"); sheet.set("B1707", "SecretInternalLinAngArrowhead547r36186")
sheet.set("A1708", "281946"); sheet.set("B1708", "EQ")
sheet.set("A1709", "281949"); sheet.set("B1709", "Arial")
sheet.set("A1710", "281954"); sheet.set("B1710", "SecretInternalRadArrowhead5473618n4")
sheet.set("A1711", "281957"); sheet.set("B1711", "EQ")
sheet.set("A1712", "281960"); sheet.set("B1712", "Arial")
sheet.set("A1713", "281965"); sheet.set("B1713", "SecretInternalTypePreviewgArrowhead5478765182")
sheet.set("A1714", "281968"); sheet.set("B1714", "C:\\pf_root\\9.0\\Data\\Platform\\Metric\\Library\\Profiles\\Structural\\")
sheet.set("A1715", "282033"); sheet.set("B1715", "Center (Front/Back)")
sheet.set("A1716", "282035"); sheet.set("B1716", "Center (Left/Right)")
sheet.set("A1717", "282050"); sheet.set("B1717", "ÿÀ")
sheet.set("A1718", "282060"); sheet.set("B1718", "EQ")
sheet.set("A1719", "288517"); sheet.set("B1719", "EQ")
sheet.set("A1720", "288520"); sheet.set("B1720", "Arial")
sheet.set("A1721", "288525"); sheet.set("B1721", "SecretInternalLinAngArrowhead547r36186")
sheet.set("A1722", "288528"); sheet.set("B1722", "EQ")
sheet.set("A1723", "288531"); sheet.set("B1723", "Arial")
sheet.set("A1724", "288536"); sheet.set("B1724", "SecretInternalRadArrowhead5473s6187")
sheet.set("A1725", "288539"); sheet.set("B1725", "EQ")
sheet.set("A1726", "288542"); sheet.set("B1726", "Arial")
sheet.set("A1727", "288547"); sheet.set("B1727", "SecretInternalTypePreviewgArrowhead5478765182")
sheet.set("A1728", "288550"); sheet.set("B1728", "C:\\Documents and Settings\\All Users\\Application Data\\Autodesk\\RAC 2009\\Metric Library\\Doors\\")
sheet.set("A1729", "288560"); sheet.set("B1729", "Floor Line")
sheet.set("A1730", "288569"); sheet.set("B1730", "Wall 1")
sheet.set("A1731", "288570"); sheet.set("B1731", "ÿM")
sheet.set("A1732", "288589"); sheet.set("B1732", "Center")
sheet.set("A1733", "288590"); sheet.set("B1733", "Left")
sheet.set("A1734", "288591"); sheet.set("B1734", "Right")
sheet.set("A1735", "288594"); sheet.set("B1735", "Top")
sheet.set("A1736", "288625"); sheet.set("B1736", "ÿ\"")
sheet.set("A1737", "288645"); sheet.set("B1737", "ÿ\"")
sheet.set("A1738", "288693"); sheet.set("B1738", "View 1")
sheet.set("A1739", "288693"); sheet.set("B1739", "ÿ;")
sheet.set("A1740", "288693"); sheet.set("B1740", "SunAndSky")
sheet.set("A1741", "288693"); sheet.set("B1741", "ÿ;")
sheet.set("A1742", "288799"); sheet.set("B1742", "Level Head - Upgrade")
sheet.set("A1743", "288812"); sheet.set("B1743", "Elevation 1")
sheet.set("A1744", "288857"); sheet.set("B1744", "Name")
sheet.set("A1745", "288882"); sheet.set("B1745", "Filled Elevation Target Ä")
sheet.set("A1746", "288888"); sheet.set("B1746", "6.35 mm")
sheet.set("A1747", "288915"); sheet.set("B1747", "Elevation")
sheet.set("A1748", "283433"); sheet.set("B1748", "EQ")
sheet.set("A1749", "283436"); sheet.set("B1749", "Arial")
sheet.set("A1750", "283441"); sheet.set("B1750", "SecretInternalLinAngArrowhead547r36186")
sheet.set("A1751", "283444"); sheet.set("B1751", "EQ")
sheet.set("A1752", "283447"); sheet.set("B1752", "Arial")
sheet.set("A1753", "283452"); sheet.set("B1753", "SecretInternalRadArrowhead5473s6187")
sheet.set("A1754", "283455"); sheet.set("B1754", "EQ")
sheet.set("A1755", "283458"); sheet.set("B1755", "Arial")
sheet.set("A1756", "283463"); sheet.set("B1756", "SecretInternalTypePreviewgArrowhead5478765182")
sheet.set("A1757", "283466"); sheet.set("B1757", "C:\\pf_root\\9.0\\Data\\Platform\\Metric\\Library\\Architectural\\Windows\\")
sheet.set("A1758", "283482"); sheet.set("B1758", "Floor Line")
sheet.set("A1759", "283491"); sheet.set("B1759", "Wall 1")
sheet.set("A1760", "283492"); sheet.set("B1760", "ÿK")
sheet.set("A1761", "283510"); sheet.set("B1761", "Center")
sheet.set("A1762", "283511"); sheet.set("B1762", "Left")
sheet.set("A1763", "283512"); sheet.set("B1763", "Right")
sheet.set("A1764", "283517"); sheet.set("B1764", "Sill")
sheet.set("A1765", "283518"); sheet.set("B1765", "Head")
sheet.set("A1766", "283521"); sheet.set("B1766", "View 1")
sheet.set("A1767", "283536"); sheet.set("B1767", "ÿl")
sheet.set("A1768", "283559"); sheet.set("B1768", "ÿ\"")
sheet.set("A1769", "283573"); sheet.set("B1769", "ÿ\"")
sheet.set("A1770", "283589"); sheet.set("B1770", "ÿ\"")
sheet.set("A1771", "300807"); sheet.set("B1771", "EQ")
sheet.set("A1772", "300810"); sheet.set("B1772", "Arial")
sheet.set("A1773", "300815"); sheet.set("B1773", "SecretInternalLinAngArrowhead54736k182")
sheet.set("A1774", "300818"); sheet.set("B1774", "EQ")
sheet.set("A1775", "300821"); sheet.set("B1775", "Arial")
sheet.set("A1776", "300826"); sheet.set("B1776", "SecretInternalRadArrowhead5473618n4")
sheet.set("A1777", "300829"); sheet.set("B1777", "EQ")
sheet.set("A1778", "300832"); sheet.set("B1778", "Arial")
sheet.set("A1779", "300837"); sheet.set("B1779", "SecretInternalTypePreviewgArrowhead5478765182")
sheet.set("A1780", "300840"); sheet.set("B1780", "C:\\pf_root\\9.0\\Data\\Platform\\Imperial\\Library\\Annotations\\")
sheet.set("A1781", "300889"); sheet.set("B1781", "A101")
sheet.set("A1782", "300922"); sheet.set("B1782", "SIM")
sheet.set("A1783", "276154"); sheet.set("B1783", "EQ")
sheet.set("A1784", "276157"); sheet.set("B1784", "Arial")
sheet.set("A1785", "276162"); sheet.set("B1785", "SecretInternalLinAngArrowhead54736k182")
sheet.set("A1786", "276165"); sheet.set("B1786", "EQ")
sheet.set("A1787", "276168"); sheet.set("B1787", "Arial")
sheet.set("A1788", "276173"); sheet.set("B1788", "SecretInternalRadArrowhead5473618n4")
sheet.set("A1789", "276176"); sheet.set("B1789", "EQ")
sheet.set("A1790", "276179"); sheet.set("B1790", "Arial")
sheet.set("A1791", "276184"); sheet.set("B1791", "SecretInternalTypePreviewgArrowhead5478765182")
sheet.set("A1792", "276187"); sheet.set("B1792", "C:\\pf_root\\9.0\\Data\\Platform\\Metric\\Library\\Annotations\\")
sheet.set("A1793", "311288"); sheet.set("B1793", "EQ")
sheet.set("A1794", "311291"); sheet.set("B1794", "Arial")
sheet.set("A1795", "311296"); sheet.set("B1795", "SecretInternalLinAngArrowhead547r36186")
sheet.set("A1796", "311299"); sheet.set("B1796", "EQ")
sheet.set("A1797", "311302"); sheet.set("B1797", "Arial")
sheet.set("A1798", "311307"); sheet.set("B1798", "SecretInternalRadArrowhead5473s6187")
sheet.set("A1799", "311310"); sheet.set("B1799", "EQ")
sheet.set("A1800", "311313"); sheet.set("B1800", "Arial")
sheet.set("A1801", "311318"); sheet.set("B1801", "SecretInternalTypePreviewgArrowhead5478765182")
sheet.set("A1802", "311321"); sheet.set("B1802", "C:\\Documents and Settings\\All Users\\Application Data\\Autodesk\\RAC 2009\\Metric Library\\Entourage\\")
sheet.set("A1803", "311356"); sheet.set("B1803", "Center (Front/Back)")
sheet.set("A1804", "311358"); sheet.set("B1804", "Center (Left/Right)")
sheet.set("A1805", "311402"); sheet.set("B1805", "Preview")
sheet.set("A1806", "311410"); sheet.set("B1806", "ÿ-")
sheet.set("A1807", "311449"); sheet.set("B1807", "Level Head - Upgrade")
sheet.set("A1808", "311462"); sheet.set("B1808", "Elevation 1")
sheet.set("A1809", "311507"); sheet.set("B1809", "Name")
sheet.set("A1810", "311532"); sheet.set("B1810", "Filled Elevation Target Ä")
sheet.set("A1811", "311538"); sheet.set("B1811", "6.35 mm")
sheet.set("A1812", "311623"); sheet.set("B1812", "{2, 15},{22, RPC-8-X9C2-NGU9-LXF5-4},{1, 0},{1, 0},{2, 15},{1, 8},{5, Color},{1, 0},{1, 0},{3, 0.8},{3, 0.8},{3, 0.8},{1, 8},{7, BBoxMin},{1, 0},{1, 0},{1, 0},{1, 0},{1, 0},{1, 8},{7, BBoxMax},{1, 0},{1, 0},{1, 0},{1, 0},{1, 0},{2, 11},{9, RPCTypeId},{1, 0},{1, 0},{22, RPC-8-X9C2-NGU9-LXF5-4},{1, 6},{14, RPCPlantHeight},{1, 0},{1, 0},{7, 5.83333},{2, 11},{7, keyword},{1, 0},{1, 0},{34, :RPCs:People [Casual]:Geometry:RPC},{2, 11},{8, category},{1, 0},{1, 0},{15, People [Casual]},{2, 11},{12, Loc")
sheet.set("A1813", "286164"); sheet.set("B1813", "EQ")
sheet.set("A1814", "286167"); sheet.set("B1814", "Arial")
sheet.set("A1815", "286172"); sheet.set("B1815", "SecretInternalLinAngArrowhead547r36186")
sheet.set("A1816", "286175"); sheet.set("B1816", "EQ")
sheet.set("A1817", "286178"); sheet.set("B1817", "Arial")
sheet.set("A1818", "286183"); sheet.set("B1818", "SecretInternalRadArrowhead5473s6187")
sheet.set("A1819", "286186"); sheet.set("B1819", "EQ")
sheet.set("A1820", "286189"); sheet.set("B1820", "Arial")
sheet.set("A1821", "286194"); sheet.set("B1821", "SecretInternalTypePreviewgArrowhead5478765182")
sheet.set("A1822", "286197"); sheet.set("B1822", "C:\\Documents and Settings\\campbes\\Desktop\\")
sheet.set("A1823", "286232"); sheet.set("B1823", "Center (Front/Back)")
sheet.set("A1824", "286234"); sheet.set("B1824", "Center (Left/Right)")
sheet.set("A1825", "286241"); sheet.set("B1825", "{3D}")
sheet.set("A1826", "286246"); sheet.set("B1826", "ÿ ")
sheet.set("A1827", "286265"); sheet.set("B1827", "ÿà")
sheet.set("A1828", "286266"); sheet.set("B1828", "ÿà")
sheet.set("A1829", "286267"); sheet.set("B1829", "ÿà")
sheet.set("A1830", "286268"); sheet.set("B1830", "ÿà")
sheet.set("A1831", "286269"); sheet.set("B1831", "ÿà")
sheet.set("A1832", "286270"); sheet.set("B1832", "ÿà")
sheet.set("A1833", "286271"); sheet.set("B1833", "ÿà")
sheet.set("A1834", "286272"); sheet.set("B1834", "ÿà")
sheet.set("A1835", "286273"); sheet.set("B1835", "ÿà")
sheet.set("A1836", "286274"); sheet.set("B1836", "ÿà")
sheet.set("A1837", "286275"); sheet.set("B1837", "ÿà")
sheet.set("A1838", "286276"); sheet.set("B1838", "ÿà")
sheet.set("A1839", "286277"); sheet.set("B1839", "ÿà")
sheet.set("A1840", "286278"); sheet.set("B1840", "ÿà")
sheet.set("A1841", "286279"); sheet.set("B1841", "ÿà")
sheet.set("A1842", "286280"); sheet.set("B1842", "ÿà")
sheet.set("A1843", "286281"); sheet.set("B1843", "ÿà")
sheet.set("A1844", "286282"); sheet.set("B1844", "ÿà")
sheet.set("A1845", "286341"); sheet.set("B1845", "Level Head - Upgrade")
sheet.set("A1846", "286354"); sheet.set("B1846", "Elevation 1")
sheet.set("A1847", "286399"); sheet.set("B1847", "Name")
sheet.set("A1848", "286424"); sheet.set("B1848", "Filled Elevation Target Ä")
sheet.set("A1849", "286430"); sheet.set("B1849", "1/4\"")
sheet.set("A1850", "208"); sheet.set("B1850", "Fill")
sheet.set("A1851", "208"); sheet.set("B1851", "ÿè")
sheet.set("A1852", "286384"); sheet.set("B1852", "_×")
sheet.set("A1853", "286384"); sheet.set("B1853", "_×")
sheet.set("A1854", "301610"); sheet.set("B1854", "EQ")
sheet.set("A1855", "301613"); sheet.set("B1855", "Arial")
sheet.set("A1856", "301618"); sheet.set("B1856", "SecretInternalLinAngArrowhead547r36186")
sheet.set("A1857", "301621"); sheet.set("B1857", "EQ")
sheet.set("A1858", "301624"); sheet.set("B1858", "Arial")
sheet.set("A1859", "301629"); sheet.set("B1859", "SecretInternalRadArrowhead5473618n4")
sheet.set("A1860", "301632"); sheet.set("B1860", "EQ")
sheet.set("A1861", "301635"); sheet.set("B1861", "Arial")
sheet.set("A1862", "301640"); sheet.set("B1862", "SecretInternalTypePreviewgArrowhead5478765182")
sheet.set("A1863", "301643"); sheet.set("B1863", "C:\\pf_root\\9.0\\Data\\Platform\\Imperial\\Library\\Annotations\\")
sheet.set("A1864", "301691"); sheet.set("B1864", "Solid Black")
sheet.set("A1865", "301738"); sheet.set("B1865", "Elevation 1")
sheet.set("A1866", "301749"); sheet.set("B1866", "Elevation 1")
sheet.set("A1867", "298798"); sheet.set("B1867", "EQ")
sheet.set("A1868", "298801"); sheet.set("B1868", "Arial")
sheet.set("A1869", "298806"); sheet.set("B1869", "SecretInternalLinAngArrowhead547r36186")
sheet.set("A1870", "298809"); sheet.set("B1870", "EQ")
sheet.set("A1871", "298812"); sheet.set("B1871", "Arial")
sheet.set("A1872", "298817"); sheet.set("B1872", "SecretInternalRadArrowhead5473s6187")
sheet.set("A1873", "298820"); sheet.set("B1873", "EQ")
sheet.set("A1874", "298823"); sheet.set("B1874", "Arial")
sheet.set("A1875", "298828"); sheet.set("B1875", "SecretInternalTypePreviewgArrowhead5478765182")
sheet.set("A1876", "298831"); sheet.set("B1876", "C:\\Documents and Settings\\All Users\\Application Data\\Autodesk\\RAC 2009\\Metric Library\\Structural\\Framing\\Concrete\\")
sheet.set("A1877", "298866"); sheet.set("B1877", "Center (Front/Back)")
sheet.set("A1878", "298868"); sheet.set("B1878", "Center (Left/Right)")
sheet.set("A1879", "298907"); sheet.set("B1879", "Member Left")
sheet.set("A1880", "298908"); sheet.set("B1880", "Member Right")
sheet.set("A1881", "298914"); sheet.set("B1881", "Bottom")
sheet.set("A1882", "298924"); sheet.set("B1882", "{3D}")
sheet.set("A1883", "298935"); sheet.set("B1883", "Left")
sheet.set("A1884", "298936"); sheet.set("B1884", "Right")
sheet.set("A1885", "298973"); sheet.set("B1885", "Level Head - Upgrade")
sheet.set("A1886", "298986"); sheet.set("B1886", "Elevation 1")
sheet.set("A1887", "299031"); sheet.set("B1887", "Name")
sheet.set("A1888", "299056"); sheet.set("B1888", "Filled Elevation Target Ä")
sheet.set("A1889", "299062"); sheet.set("B1889", "6.35 mm")
sheet.set("A1890", "299114"); sheet.set("B1890", "M_Rectangular Beam-ProfileJ")
sheet.set("A1891", "299129"); sheet.set("B1891", "M_Rectangular Beam-Profile")
sheet.set("A1892", "299134"); sheet.set("B1892", "Profile plane")
sheet.set("A1893", "299138"); sheet.set("B1893", "Start Extension")
sheet.set("A1894", "299142"); sheet.set("B1894", "Sim")
sheet.set("A1895", "284337"); sheet.set("B1895", "EQ")
sheet.set("A1896", "284340"); sheet.set("B1896", "Arial")
sheet.set("A1897", "284345"); sheet.set("B1897", "SecretInternalLinAngArrowhead547r36186")
sheet.set("A1898", "284348"); sheet.set("B1898", "EQ")
sheet.set("A1899", "284351"); sheet.set("B1899", "Arial")
sheet.set("A1900", "284356"); sheet.set("B1900", "SecretInternalRadArrowhead5473618n4")
sheet.set("A1901", "284359"); sheet.set("B1901", "EQ")
sheet.set("A1902", "284362"); sheet.set("B1902", "Arial")
sheet.set("A1903", "284367"); sheet.set("B1903", "SecretInternalTypePreviewgArrowhead5478765182")
sheet.set("A1904", "284370"); sheet.set("B1904", "D:\\Work Area\\structural\\7.0\\rotating beam\\metric profiles\\steel\\")
sheet.set("A1905", "284433"); sheet.set("B1905", "Center (Front/Back)")
sheet.set("A1906", "284435"); sheet.set("B1906", "Center (Left/Right)")
sheet.set("A1907", "284515"); sheet.set("B1907", "bf")
sheet.set("A1908", "284530"); sheet.set("B1908", "EQ")
sheet.set("A1909", "284564"); sheet.set("B1909", "EQ")
sheet.set("A1910", "281719"); sheet.set("B1910", "EQ")
sheet.set("A1911", "281722"); sheet.set("B1911", "Arial")
sheet.set("A1912", "281727"); sheet.set("B1912", "SecretInternalLinAngArrowhead54736k182")
sheet.set("A1913", "281730"); sheet.set("B1913", "EQ")
sheet.set("A1914", "281733"); sheet.set("B1914", "Arial")
sheet.set("A1915", "281738"); sheet.set("B1915", "SecretInternalRadArrowhead5473618n4")
sheet.set("A1916", "281741"); sheet.set("B1916", "EQ")
sheet.set("A1917", "281744"); sheet.set("B1917", "Arial")
sheet.set("A1918", "281749"); sheet.set("B1918", "SecretInternalTypePreviewgArrowhead5478765182")
sheet.set("A1919", "281752"); sheet.set("B1919", "C:\\pf_root\\9.0\\Data\\Platform\\Metric\\Library\\Profiles\\")
sheet.set("A1920", "281822"); sheet.set("B1920", "Center (Front/Back)")
sheet.set("A1921", "281824"); sheet.set("B1921", "Wall Face")
sheet.set("A1922", "281850"); sheet.set("B1922", "Filled Elevation Target Ä")
sheet.set("A1923", "275763"); sheet.set("B1923", "EQ")
sheet.set("A1924", "275766"); sheet.set("B1924", "Arial")
sheet.set("A1925", "275771"); sheet.set("B1925", "SecretInternalLinAngArrowhead54736k182")
sheet.set("A1926", "275774"); sheet.set("B1926", "EQ")
sheet.set("A1927", "275777"); sheet.set("B1927", "Arial")
sheet.set("A1928", "275782"); sheet.set("B1928", "SecretInternalRadArrowhead5473s6187")
sheet.set("A1929", "275785"); sheet.set("B1929", "EQ")
sheet.set("A1930", "275788"); sheet.set("B1930", "Arial")
sheet.set("A1931", "275793"); sheet.set("B1931", "SecretInternalTypePreviewgArrowhead5478765182")
sheet.set("A1932", "275796"); sheet.set("B1932", "C:\\pf_root\\9.0\\Data\\Platform\\Metric\\Library\\Annotations\\")
sheet.set("A1933", "301026"); sheet.set("B1933", "EQ")
sheet.set("A1934", "301029"); sheet.set("B1934", "Arial")
sheet.set("A1935", "301034"); sheet.set("B1935", "SecretInternalLinAngArrowhead54736k182")
sheet.set("A1936", "301037"); sheet.set("B1936", "EQ")
sheet.set("A1937", "301040"); sheet.set("B1937", "Arial")
sheet.set("A1938", "301045"); sheet.set("B1938", "SecretInternalRadArrowhead5473618n4")
sheet.set("A1939", "301048"); sheet.set("B1939", "EQ")
sheet.set("A1940", "301051"); sheet.set("B1940", "Arial")
sheet.set("A1941", "301056"); sheet.set("B1941", "SecretInternalTypePreviewgArrowhead5478765182")
sheet.set("A1942", "301059"); sheet.set("B1942", "C:\\pf_root\\9.0\\Data\\Platform\\Imperial\\Library\\Annotations\\")
sheet.set("A1943", "301106"); sheet.set("B1943", "A101")
sheet.set("A1944", "287544"); sheet.set("B1944", "EQ")
sheet.set("A1945", "287547"); sheet.set("B1945", "Arial")
sheet.set("A1946", "287552"); sheet.set("B1946", "SecretInternalLinAngArrowhead547r36186")
sheet.set("A1947", "287555"); sheet.set("B1947", "EQ")
sheet.set("A1948", "287558"); sheet.set("B1948", "Arial")
sheet.set("A1949", "287563"); sheet.set("B1949", "SecretInternalRadArrowhead5473s6187")
sheet.set("A1950", "287566"); sheet.set("B1950", "EQ")
sheet.set("A1951", "287569"); sheet.set("B1951", "Arial")
sheet.set("A1952", "287574"); sheet.set("B1952", "SecretInternalTypePreviewgArrowhead5478765182")
sheet.set("A1953", "287577"); sheet.set("B1953", "C:\\Documents and Settings\\All Users\\Application Data\\Autodesk\\RAC 2009\\Metric Library\\Planting\\")
sheet.set("A1954", "287612"); sheet.set("B1954", "Center F/B")
sheet.set("A1955", "287614"); sheet.set("B1955", "Center L/R")
sheet.set("A1956", "287621"); sheet.set("B1956", "{3D}")
sheet.set("A1957", "287665"); sheet.set("B1957", "ÿà")
sheet.set("A1958", "287666"); sheet.set("B1958", "ÿà")
sheet.set("A1959", "287667"); sheet.set("B1959", "ÿà")
sheet.set("A1960", "287668"); sheet.set("B1960", "ÿà")
sheet.set("A1961", "287669"); sheet.set("B1961", "ÿà")
sheet.set("A1962", "287670"); sheet.set("B1962", "ÿà")
sheet.set("A1963", "287671"); sheet.set("B1963", "ÿà")
sheet.set("A1964", "287672"); sheet.set("B1964", "ÿà")
sheet.set("A1965", "287673"); sheet.set("B1965", "ÿà")
sheet.set("A1966", "287674"); sheet.set("B1966", "ÿà")
sheet.set("A1967", "287675"); sheet.set("B1967", "ÿà")
sheet.set("A1968", "287676"); sheet.set("B1968", "ÿà")
sheet.set("A1969", "287677"); sheet.set("B1969", "ÿà")
sheet.set("A1970", "287678"); sheet.set("B1970", "ÿà")
sheet.set("A1971", "287679"); sheet.set("B1971", "ÿà")
sheet.set("A1972", "287680"); sheet.set("B1972", "ÿà")
sheet.set("A1973", "287681"); sheet.set("B1973", "ÿà")
sheet.set("A1974", "287682"); sheet.set("B1974", "ÿà")
sheet.set("A1975", "287683"); sheet.set("B1975", "ÿà")
sheet.set("A1976", "287684"); sheet.set("B1976", "ÿà")
sheet.set("A1977", "287685"); sheet.set("B1977", "ÿà")
sheet.set("A1978", "287686"); sheet.set("B1978", "ÿà")
sheet.set("A1979", "287687"); sheet.set("B1979", "ÿà")
sheet.set("A1980", "287688"); sheet.set("B1980", "ÿà")
sheet.set("A1981", "287689"); sheet.set("B1981", "ÿà")
sheet.set("A1982", "287690"); sheet.set("B1982", "ÿà")
sheet.set("A1983", "287691"); sheet.set("B1983", "ÿà")
sheet.set("A1984", "287692"); sheet.set("B1984", "ÿà")
sheet.set("A1985", "287693"); sheet.set("B1985", "ÿà")
sheet.set("A1986", "287694"); sheet.set("B1986", "ÿà")
sheet.set("A1987", "287695"); sheet.set("B1987", "ÿà")
sheet.set("A1988", "287696"); sheet.set("B1988", "ÿà")
sheet.set("A1989", "287697"); sheet.set("B1989", "ÿà")
sheet.set("A1990", "287698"); sheet.set("B1990", "ÿà")
sheet.set("A1991", "287699"); sheet.set("B1991", "ÿà")
sheet.set("A1992", "287700"); sheet.set("B1992", "ÿà")
sheet.set("A1993", "287701"); sheet.set("B1993", "ÿà")
sheet.set("A1994", "287702"); sheet.set("B1994", "ÿà")
sheet.set("A1995", "287703"); sheet.set("B1995", "ÿà")
sheet.set("A1996", "287704"); sheet.set("B1996", "ÿà")
sheet.set("A1997", "287705"); sheet.set("B1997", "ÿà")
sheet.set("A1998", "287706"); sheet.set("B1998", "ÿà")
sheet.set("A1999", "287745"); sheet.set("B1999", "Level Head - Upgrade")
sheet.set("A2000", "287758"); sheet.set("B2000", "Elevation 1")
sheet.set("A2001", "287803"); sheet.set("B2001", "Name")
sheet.set("A2002", "287828"); sheet.set("B2002", "Filled Elevation Target Ä")
sheet.set("A2003", "287834"); sheet.set("B2003", "6.35 mm")
sheet.set("A2004", "287925"); sheet.set("B2004", "Shrub Base")
sheet.set("A2005", "287929"); sheet.set("B2005", "{2, 15},{39, RPC-16-G0M3-8AG0-UBW3-U000-ST1L-LVER-AU},{1, 0},{1, 0},{2, 13},{1, 8},{5, Color},{1, 0},{1, 0},{3, 0.8},{3, 0.8},{3, 0.8},{1, 8},{7, BBoxMin},{1, 0},{1, 0},{1, 0},{1, 0},{1, 0},{1, 8},{7, BBoxMax},{1, 0},{1, 0},{1, 0},{1, 0},{1, 0},{2, 11},{9, RPCTypeId},{1, 0},{1, 0},{39, RPC-16-G0M3-8AG0-UBW3-U000-ST1L-LVER-AU},{1, 6},{14, RPCPlantHeight},{1, 0},{1, 0},{7, 2.62467},{2, 11},{7, keyword},{1, 0},{1, 0},{35, :RPCs:Shrubs & Grasses:Geometry:RPC},{2, 11},{8, category},{1, 0},{1, 0},{16")
sheet.set("A2006", "287949"); sheet.set("B2006", "ÖÀ")
sheet.set("A2007", "287950"); sheet.set("B2007", "Ö@")
sheet.set("A2008", "287957"); sheet.set("B2008", "Ö@")
sheet.set("A2009", "287958"); sheet.set("B2009", "ÖÀ")
sheet.set("A2010", "287977"); sheet.set("B2010", "çÀ")
sheet.set("A2011", "287979"); sheet.set("B2011", "çÀ")
sheet.set("A2012", "288001"); sheet.set("B2012", "ÖÀ")
sheet.set("A2013", "288002"); sheet.set("B2013", "Ö@")
sheet.set("A2014", "288009"); sheet.set("B2014", "Ö@")
sheet.set("A2015", "288010"); sheet.set("B2015", "ÖÀ")
sheet.set("A2016", "288061"); sheet.set("B2016", "ÖÀ")
sheet.set("A2017", "288062"); sheet.set("B2017", "ÖÀ")
sheet.set("A2018", "288063"); sheet.set("B2018", "ÖÀ")
sheet.set("A2019", "288064"); sheet.set("B2019", "ÖÀ")
sheet.set("A2020", "288091"); sheet.set("B2020", "Ö@")
sheet.set("A2021", "288092"); sheet.set("B2021", "Ö@")
sheet.set("A2022", "288093"); sheet.set("B2022", "Ö@")
sheet.set("A2023", "288094"); sheet.set("B2023", "Ö@")
sheet.set("A2024", "288097"); sheet.set("B2024", "Shrub Base*")
sheet.set("A2025", "282564"); sheet.set("B2025", "EQ")
sheet.set("A2026", "282567"); sheet.set("B2026", "Arial")
sheet.set("A2027", "282572"); sheet.set("B2027", "SecretInternalLinAngArrowhead547r36186")
sheet.set("A2028", "282575"); sheet.set("B2028", "EQ")
sheet.set("A2029", "282578"); sheet.set("B2029", "Arial")
sheet.set("A2030", "282583"); sheet.set("B2030", "SecretInternalRadArrowhead5473s6187")
sheet.set("A2031", "282586"); sheet.set("B2031", "EQ")
sheet.set("A2032", "282589"); sheet.set("B2032", "Arial")
sheet.set("A2033", "282594"); sheet.set("B2033", "SecretInternalTypePreviewgArrowhead5478765182")
sheet.set("A2034", "282597"); sheet.set("B2034", "C:\\pf_root\\9.0\\Data\\Platform\\Metric\\Library\\Architectural\\Balusters\\")
sheet.set("A2035", "282609"); sheet.set("B2035", "Ref. Level")
sheet.set("A2036", "282634"); sheet.set("B2036", "Center (Front/Back)")
sheet.set("A2037", "282636"); sheet.set("B2037", "Center (Left/Right)")
sheet.set("A2038", "282682"); sheet.set("B2038", "Top")
sheet.set("A2039", "282690"); sheet.set("B2039", "View 1")
sheet.set("A2040", "282695"); sheet.set("B2040", "Top Angle Cut")
sheet.set("A2041", "282716"); sheet.set("B2041", "ÿ\"")
sheet.set("A2042", "282717"); sheet.set("B2042", "ÿi")
sheet.set("A2043", "282721"); sheet.set("B2043", "ÿl")
sheet.set("A2044", "282753"); sheet.set("B2044", "Level Head - Upgrade")
sheet.set("A2045", "282766"); sheet.set("B2045", "Elevation 1")
sheet.set("A2046", "282811"); sheet.set("B2046", "Name")
sheet.set("A2047", "282836"); sheet.set("B2047", "Filled Elevation Target Ä")
sheet.set("A2048", "282842"); sheet.set("B2048", "6.35 mm")
sheet.set("A2049", "282860"); sheet.set("B2049", "Bottom Angle Cut")
sheet.set("A2050", "282872"); sheet.set("B2050", "Building Section 1")
sheet.set("A2051", "286557"); sheet.set("B2051", "EQ")
sheet.set("A2052", "286560"); sheet.set("B2052", "Arial")
sheet.set("A2053", "286565"); sheet.set("B2053", "SecretInternalLinAngArrowhead547r36186")
sheet.set("A2054", "286568"); sheet.set("B2054", "EQ")
sheet.set("A2055", "286571"); sheet.set("B2055", "Arial")
sheet.set("A2056", "286576"); sheet.set("B2056", "SecretInternalRadArrowhead5473s6187")
sheet.set("A2057", "286579"); sheet.set("B2057", "EQ")
sheet.set("A2058", "286582"); sheet.set("B2058", "Arial")
sheet.set("A2059", "286587"); sheet.set("B2059", "SecretInternalTypePreviewgArrowhead5478765182")
sheet.set("A2060", "286590"); sheet.set("B2060", "D:\\RPC Families From Steve\\20080108\\Metric\\")
sheet.set("A2061", "286600"); sheet.set("B2061", "Ground floor")
sheet.set("A2062", "299192"); sheet.set("B2062", "EQ")
sheet.set("A2063", "299195"); sheet.set("B2063", "Arial")
sheet.set("A2064", "299200"); sheet.set("B2064", "SecretInternalLinAngArrowhead547r36186")
sheet.set("A2065", "299203"); sheet.set("B2065", "EQ")
sheet.set("A2066", "299206"); sheet.set("B2066", "Arial")
sheet.set("A2067", "299211"); sheet.set("B2067", "SecretInternalRadArrowhead5473s6187")
sheet.set("A2068", "299214"); sheet.set("B2068", "EQ")
sheet.set("A2069", "299217"); sheet.set("B2069", "Arial")
sheet.set("A2070", "299222"); sheet.set("B2070", "SecretInternalTypePreviewgArrowhead5478765182")
sheet.set("A2071", "299225"); sheet.set("B2071", "C:\\Documents and Settings\\All Users\\Application Data\\Autodesk\\RAC 2009\\Metric Library\\Detail Components\\Div 04-Masonry\\04220-Concrete Masonry Units\\")
sheet.set("A2072", "299240"); sheet.set("B2072", "Center (Front/Back)")
sheet.set("A2073", "299242"); sheet.set("B2073", "Center (Left/Right)")
sheet.set("A2074", "299407"); sheet.set("B2074", "Right")
sheet.set("A2075", "299423"); sheet.set("B2075", "Mortar Visibility")
sheet.set("A2076", "299434"); sheet.set("B2076", "Face")
sheet.set("A2077", "299464"); sheet.set("B2077", "Core Visibility")
sheet.set("A2078", "299466"); sheet.set("B2078", "Web")
sheet.set("A2079", "308428"); sheet.set("B2079", "EQ")
sheet.set("A2080", "308431"); sheet.set("B2080", "Arial")
sheet.set("A2081", "308436"); sheet.set("B2081", "SecretInternalLinAngArrowhead547r36186")
sheet.set("A2082", "308439"); sheet.set("B2082", "EQ")
sheet.set("A2083", "308442"); sheet.set("B2083", "Arial")
sheet.set("A2084", "308447"); sheet.set("B2084", "SecretInternalRadArrowhead5473s6187")
sheet.set("A2085", "308450"); sheet.set("B2085", "EQ")
sheet.set("A2086", "308453"); sheet.set("B2086", "Arial")
sheet.set("A2087", "308458"); sheet.set("B2087", "SecretInternalTypePreviewgArrowhead5478765182")
sheet.set("A2088", "308461"); sheet.set("B2088", "C:\\Documents and Settings\\All Users\\Application Data\\Autodesk\\RAC 2009\\Metric Library\\Doors\\")
sheet.set("A2089", "308471"); sheet.set("B2089", "Ground floor")
sheet.set("A2090", "308480"); sheet.set("B2090", "Wall 1")
sheet.set("A2091", "308481"); sheet.set("B2091", "ÿ5")
sheet.set("A2092", "308533"); sheet.set("B2092", "View 1")
sheet.set("A2093", "308547"); sheet.set("B2093", "ÿ\"")
sheet.set("A2094", "308592"); sheet.set("B2094", "Elevation 1")
sheet.set("A2095", "308595"); sheet.set("B2095", "Q@")
sheet.set("A2096", "308598"); sheet.set("B2096", "ÿ\"")
sheet.set("A2097", "308618"); sheet.set("B2097", "ÿ\"")
sheet.set("A2098", "308639"); sheet.set("B2098", "ÿl")
sheet.set("A2099", "308656"); sheet.set("B2099", "!À")
sheet.set("A2100", "308737"); sheet.set("B2100", "Level Head - Upgrade")
sheet.set("A2101", "308750"); sheet.set("B2101", "Elevation 1")
sheet.set("A2102", "308795"); sheet.set("B2102", "Name")
sheet.set("A2103", "308820"); sheet.set("B2103", "Filled Elevation Target Ä")
sheet.set("A2104", "308826"); sheet.set("B2104", "6.35 mm")
sheet.set("A2105", "308849"); sheet.set("B2105", "Elevation")
sheet.set("A2106", "297794"); sheet.set("B2106", "EQ")
sheet.set("A2107", "297797"); sheet.set("B2107", "Arial")
sheet.set("A2108", "297802"); sheet.set("B2108", "SecretInternalLinAngArrowhead547r36186")
sheet.set("A2109", "297805"); sheet.set("B2109", "EQ")
sheet.set("A2110", "297808"); sheet.set("B2110", "Arial")
sheet.set("A2111", "297813"); sheet.set("B2111", "SecretInternalRadArrowhead5473s6187")
sheet.set("A2112", "297816"); sheet.set("B2112", "EQ")
sheet.set("A2113", "297819"); sheet.set("B2113", "Arial")
sheet.set("A2114", "297824"); sheet.set("B2114", "SecretInternalTypePreviewgArrowhead5478765182")
sheet.set("A2115", "297827"); sheet.set("B2115", "C:\\Documents and Settings\\All Users\\Application Data\\Autodesk\\RAC 2009\\Metric Library\\Structural\\Framing\\Steel\\")
sheet.set("A2116", "297862"); sheet.set("B2116", "Center (Front/Back)")
sheet.set("A2117", "297864"); sheet.set("B2117", "Center (Left/Right)")
sheet.set("A2118", "297903"); sheet.set("B2118", "Member Left")
sheet.set("A2119", "297904"); sheet.set("B2119", "Member Right")
sheet.set("A2120", "297919"); sheet.set("B2120", "{3D}")
sheet.set("A2121", "297927"); sheet.set("B2121", "Left")
sheet.set("A2122", "297928"); sheet.set("B2122", "Stick Symbol Left")
sheet.set("A2123", "297929"); sheet.set("B2123", "Stick Symbol Right")
sheet.set("A2124", "297930"); sheet.set("B2124", "Right")
sheet.set("A2125", "297966"); sheet.set("B2125", "Level Head - Upgrade")
sheet.set("A2126", "297979"); sheet.set("B2126", "Elevation 1")
sheet.set("A2127", "298024"); sheet.set("B2127", "Name")
sheet.set("A2128", "298049"); sheet.set("B2128", "Filled Elevation Target Ä")
sheet.set("A2129", "298055"); sheet.set("B2129", "1/4\"")
sheet.set("A2130", "298187"); sheet.set("B2130", "ÿ2")
sheet.set("A2131", "298216"); sheet.set("B2131", "ÿ2")
sheet.set("A2132", "298247"); sheet.set("B2132", "ÿ2")
sheet.set("A2133", "298276"); sheet.set("B2133", "ÿ2")
sheet.set("A2134", "298313"); sheet.set("B2134", "ÿ$")
sheet.set("A2135", "298316"); sheet.set("B2135", "Profile plane")
sheet.set("A2136", "298339"); sheet.set("B2136", "ÿ:")
sheet.set("A2137", "298342"); sheet.set("B2137", "Profile plane")
sheet.set("A2138", "298344"); sheet.set("B2138", "Web-Profile1")
sheet.set("A2139", "298358"); sheet.set("B2139", "Web-Profile1")
sheet.set("A2140", "298360"); sheet.set("B2140", "ÿ\"")
sheet.set("A2141", "298363"); sheet.set("B2141", "Profile plane")
sheet.set("A2142", "298388"); sheet.set("B2142", "PanelWidth")
sheet.set("A2143", "298400"); sheet.set("B2143", "Array Group 1")
sheet.set("A2144", "298445"); sheet.set("B2144", "Profile plane")
sheet.set("A2145", "298452"); sheet.set("B2145", "Arial")
sheet.set("A2146", "298461"); sheet.set("B2146", "EQ")
sheet.set("A2147", "298471"); sheet.set("B2147", "Sim")
sheet.set("A2148", "298475"); sheet.set("B2148", "Angled Web")
sheet.set("A2149", "298504"); sheet.set("B2149", "EQ")
sheet.set("A2150", "298542"); sheet.set("B2150", "÷=")
sheet.set("A2151", "281472"); sheet.set("B2151", "EQ")
sheet.set("A2152", "281475"); sheet.set("B2152", "Arial")
sheet.set("A2153", "281480"); sheet.set("B2153", "SecretInternalLinAngArrowhead547r36186")
sheet.set("A2154", "281483"); sheet.set("B2154", "EQ")
sheet.set("A2155", "281486"); sheet.set("B2155", "Arial")
sheet.set("A2156", "281491"); sheet.set("B2156", "SecretInternalRadArrowhead5473618n4")
sheet.set("A2157", "281494"); sheet.set("B2157", "EQ")
sheet.set("A2158", "281497"); sheet.set("B2158", "Arial")
sheet.set("A2159", "281502"); sheet.set("B2159", "SecretInternalTypePreviewgArrowhead5478765182")
sheet.set("A2160", "281505"); sheet.set("B2160", "C:\\pf_root\\9.0\\Data\\Platform\\Metric\\Library\\Profiles\\Roofs\\")
sheet.set("A2161", "281573"); sheet.set("B2161", "ÿ9")
sheet.set("A2162", "281582"); sheet.set("B2162", "EQ")
sheet.set("A2163", "279764"); sheet.set("B2163", "EQ")
sheet.set("A2164", "279767"); sheet.set("B2164", "Arial")
sheet.set("A2165", "279772"); sheet.set("B2165", "SecretInternalLinAngArrowhead547r36186")
sheet.set("A2166", "279775"); sheet.set("B2166", "EQ")
sheet.set("A2167", "279778"); sheet.set("B2167", "Arial")
sheet.set("A2168", "279783"); sheet.set("B2168", "SecretInternalRadArrowhead5473s6187")
sheet.set("A2169", "279786"); sheet.set("B2169", "EQ")
sheet.set("A2170", "279789"); sheet.set("B2170", "Arial")
sheet.set("A2171", "279794"); sheet.set("B2171", "SecretInternalTypePreviewgArrowhead5478765182")
sheet.set("A2172", "279797"); sheet.set("B2172", "C:\\pf_root\\9.0\\Data\\Platform\\Metric\\Library\\Architectural\\Doors\\")
sheet.set("A2173", "279812"); sheet.set("B2173", "Ground floor")
sheet.set("A2174", "279821"); sheet.set("B2174", "Wall 1")
sheet.set("A2175", "279822"); sheet.set("B2175", "ÿ5")
sheet.set("A2176", "279842"); sheet.set("B2176", "ÞÀ")
sheet.set("A2177", "279843"); sheet.set("B2177", "ÞÀ")
sheet.set("A2178", "279844"); sheet.set("B2178", "ÞÀ")
sheet.set("A2179", "279847"); sheet.set("B2179", "ÞÀ")
sheet.set("A2180", "279881"); sheet.set("B2180", "ÞÀ")
sheet.set("A2181", "279916"); sheet.set("B2181", "ÿ\"")
sheet.set("A2182", "279932"); sheet.set("B2182", "ÿ\"")
sheet.set("A2183", "279942"); sheet.set("B2183", "View ")
sheet.set("A2184", "279962"); sheet.set("B2184", "ÞÀ")
sheet.set("A2185", "279963"); sheet.set("B2185", "ÞÀ")
sheet.set("A2186", "279964"); sheet.set("B2186", "ÞÀ")
sheet.set("A2187", "280026"); sheet.set("B2187", "Level Head - Upgrade")
sheet.set("A2188", "280039"); sheet.set("B2188", "Elevation 1")
sheet.set("A2189", "280084"); sheet.set("B2189", "Name")
sheet.set("A2190", "280109"); sheet.set("B2190", "Filled Elevation Target Ä")
sheet.set("A2191", "280115"); sheet.set("B2191", "6.35 mm")
sheet.set("A2192", "280143"); sheet.set("B2192", "Elevation")
sheet.set("A2193", "299722"); sheet.set("B2193", "EQ")
sheet.set("A2194", "299725"); sheet.set("B2194", "Arial")
sheet.set("A2195", "299730"); sheet.set("B2195", "SecretInternalLinAngArrowhead547r36186")
sheet.set("A2196", "299733"); sheet.set("B2196", "EQ")
sheet.set("A2197", "299736"); sheet.set("B2197", "Arial")
sheet.set("A2198", "299741"); sheet.set("B2198", "SecretInternalRadArrowhead5473s6187")
sheet.set("A2199", "299744"); sheet.set("B2199", "EQ")
sheet.set("A2200", "299747"); sheet.set("B2200", "Arial")
sheet.set("A2201", "299752"); sheet.set("B2201", "SecretInternalTypePreviewgArrowhead5478765182")
sheet.set("A2202", "299755"); sheet.set("B2202", "C:\\Documents and Settings\\All Users\\Application Data\\Autodesk\\RAC 2009\\Imperial Library\\Detail Components\\Structural\\Concrete\\")
sheet.set("A2203", "299770"); sheet.set("B2203", "Center (Front/Back)")
sheet.set("A2204", "299772"); sheet.set("B2204", "Center (Left/Right)")
sheet.set("A2205", "299818"); sheet.set("B2205", "Reinforcing Steel")
sheet.set("A2206", "299839"); sheet.set("B2206", "Revealy")
sheet.set("A2207", "299492"); sheet.set("B2207", "EQ")
sheet.set("A2208", "299495"); sheet.set("B2208", "Arial")
sheet.set("A2209", "299500"); sheet.set("B2209", "SecretInternalLinAngArrowhead54736k182")
sheet.set("A2210", "299503"); sheet.set("B2210", "EQ")
sheet.set("A2211", "299506"); sheet.set("B2211", "Arial")
sheet.set("A2212", "299511"); sheet.set("B2212", "SecretInternalRadArrowhead5473s6187")
sheet.set("A2213", "299514"); sheet.set("B2213", "EQ")
sheet.set("A2214", "299517"); sheet.set("B2214", "Arial")
sheet.set("A2215", "299522"); sheet.set("B2215", "SecretInternalTypePreviewgArrowhead5478765182")
sheet.set("A2216", "299525"); sheet.set("B2216", "C:\\Documents and Settings\\All Users\\Application Data\\Autodesk\\RAC 2009\\Metric Library\\Detail Components\\Structural\\Concrete\\")
sheet.set("A2217", "299540"); sheet.set("B2217", "Center (Front/Back)")
sheet.set("A2218", "299542"); sheet.set("B2218", "Center (Left/Right)")
sheet.set("A2219", "299585"); sheet.set("B2219", "Bar Diameter")
sheet.set("A2220", "299599"); sheet.set("B2220", "Reinforcing Steel")
sheet.set("A2221", "299609"); sheet.set("B2221", "L1")
sheet.set("A2222", "299613"); sheet.set("B2222", "Revealy")
sheet.set("A2223", "277671"); sheet.set("B2223", "EQ")
sheet.set("A2224", "277674"); sheet.set("B2224", "Arial")
sheet.set("A2225", "277679"); sheet.set("B2225", "SecretInternalLinAngArrowhead54736k182")
sheet.set("A2226", "277682"); sheet.set("B2226", "EQ")
sheet.set("A2227", "277685"); sheet.set("B2227", "Arial")
sheet.set("A2228", "277690"); sheet.set("B2228", "SecretInternalRadArrowhead5473618n4")
sheet.set("A2229", "277693"); sheet.set("B2229", "EQ")
sheet.set("A2230", "277696"); sheet.set("B2230", "Arial")
sheet.set("A2231", "277701"); sheet.set("B2231", "SecretInternalTypePreviewgArrowhead5478765182")
sheet.set("A2232", "277704"); sheet.set("B2232", "C:\\pf_root\\9.0\\Data\\Platform\\Metric\\Library\\Annotations\\")
sheet.set("A2233", "277717"); sheet.set("B2233", "Baseline")
sheet.set("A2234", "277751"); sheet.set("B2234", "A101")
sheet.set("A2235", "276511"); sheet.set("B2235", "EQ")
sheet.set("A2236", "276514"); sheet.set("B2236", "Arial")
sheet.set("A2237", "276519"); sheet.set("B2237", "SecretInternalLinAngArrowhead547r36186")
sheet.set("A2238", "276522"); sheet.set("B2238", "EQ")
sheet.set("A2239", "276525"); sheet.set("B2239", "Arial")
sheet.set("A2240", "276530"); sheet.set("B2240", "SecretInternalRadArrowhead5473s6187")
sheet.set("A2241", "276533"); sheet.set("B2241", "EQ")
sheet.set("A2242", "276536"); sheet.set("B2242", "Arial")
sheet.set("A2243", "276541"); sheet.set("B2243", "SecretInternalTypePreviewgArrowhead5478765182")
sheet.set("A2244", "276544"); sheet.set("B2244", "C:\\pf_root\\9.0\\Data\\Platform\\Metric\\Library\\Annotations\\")
sheet.set("A2245", "276620"); sheet.set("B2245", "Filled Elevation Target Ä")
sheet.set("A2246", "304977"); sheet.set("B2246", "EQ")
sheet.set("A2247", "304980"); sheet.set("B2247", "Arial")
sheet.set("A2248", "304985"); sheet.set("B2248", "SecretInternalLinAngArrowhead547r36186")
sheet.set("A2249", "304988"); sheet.set("B2249", "EQ")
sheet.set("A2250", "304991"); sheet.set("B2250", "Arial")
sheet.set("A2251", "304996"); sheet.set("B2251", "SecretInternalRadArrowhead5473s6187")
sheet.set("A2252", "304999"); sheet.set("B2252", "EQ")
sheet.set("A2253", "305002"); sheet.set("B2253", "Arial")
sheet.set("A2254", "305007"); sheet.set("B2254", "SecretInternalTypePreviewgArrowhead5478765182")
sheet.set("A2255", "305010"); sheet.set("B2255", "C:\\Documents and Settings\\All Users\\Application Data\\Autodesk\\RAC 2009\\Imperial Library\\")
sheet.set("A2256", "305020"); sheet.set("B2256", "Ref. Level")
sheet.set("A2257", "305048"); sheet.set("B2257", "View 1")
sheet.set("A2258", "305071"); sheet.set("B2258", "ÿr")
sheet.set("A2259", "305113"); sheet.set("B2259", "ÿZ")
sheet.set("A2260", "305137"); sheet.set("B2260", "ÿl")
sheet.set("A2261", "305222"); sheet.set("B2261", "Level Head - Upgrade")
sheet.set("A2262", "305970"); sheet.set("B2262", "EQ")
sheet.set("A2263", "305973"); sheet.set("B2263", "Arial")
sheet.set("A2264", "305978"); sheet.set("B2264", "SecretInternalLinAngArrowhead547r36186")
sheet.set("A2265", "305981"); sheet.set("B2265", "EQ")
sheet.set("A2266", "305984"); sheet.set("B2266", "Arial")
sheet.set("A2267", "305989"); sheet.set("B2267", "SecretInternalRadArrowhead5473s6187")
sheet.set("A2268", "305992"); sheet.set("B2268", "EQ")
sheet.set("A2269", "305995"); sheet.set("B2269", "Arial")
sheet.set("A2270", "306000"); sheet.set("B2270", "SecretInternalTypePreviewgArrowhead5478765182")
sheet.set("A2271", "306003"); sheet.set("B2271", "C:\\Documents and Settings\\All Users\\Application Data\\Autodesk\\RAC 2009\\Imperial Library\\Planting\\")
sheet.set("A2272", "306038"); sheet.set("B2272", "Center F/B")
sheet.set("A2273", "306040"); sheet.set("B2273", "Center L/R")
sheet.set("A2274", "306047"); sheet.set("B2274", "{3D}")
sheet.set("A2275", "306089"); sheet.set("B2275", "ÿ}")
sheet.set("A2276", "306093"); sheet.set("B2276", "ÿà")
sheet.set("A2277", "306094"); sheet.set("B2277", "ÿà")
sheet.set("A2278", "306095"); sheet.set("B2278", "ÿà")
sheet.set("A2279", "306096"); sheet.set("B2279", "ÿà")
sheet.set("A2280", "306097"); sheet.set("B2280", "ÿà")
sheet.set("A2281", "306098"); sheet.set("B2281", "ÿà")
sheet.set("A2282", "306099"); sheet.set("B2282", "ÿà")
sheet.set("A2283", "306100"); sheet.set("B2283", "ÿà")
sheet.set("A2284", "306101"); sheet.set("B2284", "ÿà")
sheet.set("A2285", "306102"); sheet.set("B2285", "ÿà")
sheet.set("A2286", "306103"); sheet.set("B2286", "ÿà")
sheet.set("A2287", "306104"); sheet.set("B2287", "ÿà")
sheet.set("A2288", "306105"); sheet.set("B2288", "ÿà")
sheet.set("A2289", "306106"); sheet.set("B2289", "ÿà")
sheet.set("A2290", "306107"); sheet.set("B2290", "ÿà")
sheet.set("A2291", "306108"); sheet.set("B2291", "ÿà")
sheet.set("A2292", "306109"); sheet.set("B2292", "ÿà")
sheet.set("A2293", "306110"); sheet.set("B2293", "ÿà")
sheet.set("A2294", "306111"); sheet.set("B2294", "ÿà")
sheet.set("A2295", "306112"); sheet.set("B2295", "ÿà")
sheet.set("A2296", "306113"); sheet.set("B2296", "ÿà")
sheet.set("A2297", "306114"); sheet.set("B2297", "ÿà")
sheet.set("A2298", "306115"); sheet.set("B2298", "ÿà")
sheet.set("A2299", "306116"); sheet.set("B2299", "ÿà")
sheet.set("A2300", "306117"); sheet.set("B2300", "ÿà")
sheet.set("A2301", "306118"); sheet.set("B2301", "ÿà")
sheet.set("A2302", "306119"); sheet.set("B2302", "ÿà")
sheet.set("A2303", "306120"); sheet.set("B2303", "ÿà")
sheet.set("A2304", "306121"); sheet.set("B2304", "ÿà")
sheet.set("A2305", "306122"); sheet.set("B2305", "ÿà")
sheet.set("A2306", "306123"); sheet.set("B2306", "ÿà")
sheet.set("A2307", "306124"); sheet.set("B2307", "ÿà")
sheet.set("A2308", "306125"); sheet.set("B2308", "ÿà")
sheet.set("A2309", "306126"); sheet.set("B2309", "ÿà")
sheet.set("A2310", "306127"); sheet.set("B2310", "ÿà")
sheet.set("A2311", "306128"); sheet.set("B2311", "ÿà")
sheet.set("A2312", "306129"); sheet.set("B2312", "ÿà")
sheet.set("A2313", "306130"); sheet.set("B2313", "ÿà")
sheet.set("A2314", "306131"); sheet.set("B2314", "ÿà")
sheet.set("A2315", "306132"); sheet.set("B2315", "ÿà")
sheet.set("A2316", "306133"); sheet.set("B2316", "ÿà")
sheet.set("A2317", "306134"); sheet.set("B2317", "ÿà")
sheet.set("A2318", "306173"); sheet.set("B2318", "Level Head - Upgrade")
sheet.set("A2319", "306186"); sheet.set("B2319", "Elevation 1")
sheet.set("A2320", "306231"); sheet.set("B2320", "Name")
sheet.set("A2321", "306256"); sheet.set("B2321", "Filled Elevation Target Ä")
sheet.set("A2322", "306262"); sheet.set("B2322", "1/4\"")
sheet.set("A2323", "306355"); sheet.set("B2323", "{2, 15},{39, RPC-16-G0M3-8AG0-UBW3-U000-ST1L-LVER-AU},{1, 0},{1, 0},{2, 13},{1, 8},{5, Color},{1, 0},{1, 0},{3, 0.8},{3, 0.8},{3, 0.8},{1, 8},{7, BBoxMin},{1, 0},{1, 0},{1, 0},{1, 0},{1, 0},{1, 8},{7, BBoxMax},{1, 0},{1, 0},{1, 0},{1, 0},{1, 0},{2, 11},{9, RPCTypeId},{1, 0},{1, 0},{39, RPC-16-G0M3-8AG0-UBW3-U000-ST1L-LVER-AU},{1, 6},{14, RPCPlantHeight},{1, 0},{1, 0},{4, 2.75},{2, 11},{7, keyword},{1, 0},{1, 0},{35, :RPCs:Shrubs & Grasses:Geometry:RPC},{2, 11},{8, category},{1, 0},{1, 0},{16, S")
sheet.set("A2324", "306356"); sheet.set("B2324", "Shrub Base*")
sheet.set("A2325", "305437"); sheet.set("B2325", "EQ")
sheet.set("A2326", "305440"); sheet.set("B2326", "Arial")
sheet.set("A2327", "305445"); sheet.set("B2327", "SecretInternalLinAngArrowhead54736k182")
sheet.set("A2328", "305448"); sheet.set("B2328", "EQ")
sheet.set("A2329", "305451"); sheet.set("B2329", "Arial")
sheet.set("A2330", "305456"); sheet.set("B2330", "SecretInternalRadArrowhead5473618n4")
sheet.set("A2331", "305459"); sheet.set("B2331", "EQ")
sheet.set("A2332", "305462"); sheet.set("B2332", "Arial")
sheet.set("A2333", "305467"); sheet.set("B2333", "SecretInternalTypePreviewgArrowhead5478765182")
sheet.set("A2334", "305517"); sheet.set("B2334", "Solid Black")
sheet.set("A2335", "305558"); sheet.set("B2335", "all")
sheet.set("A2336", "310057"); sheet.set("B2336", "EQ")
sheet.set("A2337", "310060"); sheet.set("B2337", "Arial")
sheet.set("A2338", "310065"); sheet.set("B2338", "SecretInternalLinAngArrowhead547r36186")
sheet.set("A2339", "310068"); sheet.set("B2339", "EQ")
sheet.set("A2340", "310071"); sheet.set("B2340", "Arial")
sheet.set("A2341", "310076"); sheet.set("B2341", "SecretInternalRadArrowhead5473s6187")
sheet.set("A2342", "310079"); sheet.set("B2342", "EQ")
sheet.set("A2343", "310082"); sheet.set("B2343", "Arial")
sheet.set("A2344", "310087"); sheet.set("B2344", "SecretInternalTypePreviewgArrowhead5478765182")
sheet.set("A2345", "310090"); sheet.set("B2345", "C:\\Documents and Settings\\hansonje\\Desktop\\")
sheet.set("A2346", "310100"); sheet.set("B2346", "Ref. Level")
sheet.set("A2347", "310109"); sheet.set("B2347", "Wall 1")
sheet.set("A2348", "310110"); sheet.set("B2348", "ÿM")
sheet.set("A2349", "310131"); sheet.set("B2349", "Curtain Wall 1")
sheet.set("A2350", "310133"); sheet.set("B2350", "View 1")
sheet.set("A2351", "310156"); sheet.set("B2351", "Light Source Axis")
sheet.set("A2352", "310157"); sheet.set("B2352", "Light Source Axis")
sheet.set("A2353", "310158"); sheet.set("B2353", "Light Source Elevation")
sheet.set("A2354", "310235"); sheet.set("B2354", "Level Head - Upgrade")
sheet.set("A2355", "310248"); sheet.set("B2355", "Elevation 1")
sheet.set("A2356", "310293"); sheet.set("B2356", "Name")
sheet.set("A2357", "310318"); sheet.set("B2357", "Filled Elevation Target Ä")
sheet.set("A2358", "310324"); sheet.set("B2358", "1/4\"")
sheet.set("A2359", "310449"); sheet.set("B2359", "Profile plane")
sheet.set("A2360", "310571"); sheet.set("B2360", "Wall 2")
sheet.set("A2361", "310579"); sheet.set("B2361", "Profile plane")
sheet.set("A2362", "310595"); sheet.set("B2362", "EQ")
sheet.set("A2363", "295457"); sheet.set("B2363", "EQ")
sheet.set("A2364", "295460"); sheet.set("B2364", "Arial")
sheet.set("A2365", "295465"); sheet.set("B2365", "SecretInternalLinAngArrowhead547r36186")
sheet.set("A2366", "67404321"); sheet.set("B2366", "alLinAngArrowhead547r36")
sheet.set("A2367", "295466"); sheet.set("B2367", "48")
sheet.set("A2368", "295466"); sheet.set("B2368", "De")
sheet.set("A2369", "295725"); sheet.set("B2369", "Level Head - Upgrade")
sheet.set("A2370", "295738"); sheet.set("B2370", "Elevation 1")
sheet.set("A2371", "295783"); sheet.set("B2371", "Name")
sheet.set("A2372", "295808"); sheet.set("B2372", "Filled Elevation Target Ä")
sheet.set("A2373", "295814"); sheet.set("B2373", "6.35 mm")
sheet.set("A2374", "282153"); sheet.set("B2374", "EQ")
sheet.set("A2375", "282156"); sheet.set("B2375", "Arial")
sheet.set("A2376", "282161"); sheet.set("B2376", "SecretInternalLinAngArrowhead547r36186")
sheet.set("A2377", "282164"); sheet.set("B2377", "EQ")
sheet.set("A2378", "282167"); sheet.set("B2378", "Arial")
sheet.set("A2379", "282172"); sheet.set("B2379", "SecretInternalRadArrowhead5473s6187")
sheet.set("A2380", "282175"); sheet.set("B2380", "EQ")
sheet.set("A2381", "282178"); sheet.set("B2381", "Arial")
sheet.set("A2382", "282183"); sheet.set("B2382", "SecretInternalTypePreviewgArrowhead5478765182")
sheet.set("A2383", "282186"); sheet.set("B2383", "C:\\pf_root\\9.0\\Data\\Platform\\Metric\\Library\\Architectural\\Balusters\\")
sheet.set("A2384", "282198"); sheet.set("B2384", "Ref. Level")
sheet.set("A2385", "282223"); sheet.set("B2385", "Center (Front/Back)")
sheet.set("A2386", "282225"); sheet.set("B2386", "Center (Left/Right)")
sheet.set("A2387", "282271"); sheet.set("B2387", "Top")
sheet.set("A2388", "282279"); sheet.set("B2388", "View 1")
sheet.set("A2389", "282284"); sheet.set("B2389", "Top Angle Cut")
sheet.set("A2390", "282294"); sheet.set("B2390", "al0")
sheet.set("A2391", "282292"); sheet.set("B2391", "al")
sheet.set("A2392", "1079594676"); sheet.set("B2392", "al")
sheet.set("A2393", "2338148020"); sheet.set("B2393", "al")
sheet.set("A2394", "2338148020"); sheet.set("B2394", "alal")
sheet.set("A2395", "282292"); sheet.set("B2395", "al")
sheet.set("A2396", "2338148020"); sheet.set("B2396", "b+")
sheet.set("A2397", "2338148020"); sheet.set("B2397", "?ÿ")
sheet.set("A2398", "282454"); sheet.set("B2398", "0@")
sheet.set("A2399", "282462"); sheet.set("B2399", "Building Section 1")
sheet.set("A2400", "278243"); sheet.set("B2400", "EQ")
sheet.set("A2401", "278246"); sheet.set("B2401", "Arial")
sheet.set("A2402", "278251"); sheet.set("B2402", "SecretInternalLinAngArrowhead54736k182")
sheet.set("A2403", "278254"); sheet.set("B2403", "EQ")
sheet.set("A2404", "278257"); sheet.set("B2404", "Arial")
sheet.set("A2405", "278262"); sheet.set("B2405", "SecretInternalRadArrowhead5473618n4")
sheet.set("A2406", "278265"); sheet.set("B2406", "EQ")
sheet.set("A2407", "278268"); sheet.set("B2407", "Arial")
sheet.set("A2408", "278273"); sheet.set("B2408", "SecretInternalTypePreviewgArrowhead5478765182")
sheet.set("A2409", "278276"); sheet.set("B2409", "C:\\pf_root\\9.0\\Data\\Platform\\Metric\\Library\\Annotations\\")
sheet.set("A2410", "278324"); sheet.set("B2410", "Solid Black")
sheet.set("A2411", "278373"); sheet.set("B2411", "Elevation 1")
sheet.set("A2412", "278382"); sheet.set("B2412", "Elevation 1")
sheet.set("A2413", "278631"); sheet.set("B2413", "EQ")
sheet.set("A2414", "278634"); sheet.set("B2414", "Arial")
sheet.set("A2415", "278639"); sheet.set("B2415", "SecretInternalLinAngArrowhead54736k182")
sheet.set("A2416", "278642"); sheet.set("B2416", "EQ")
sheet.set("A2417", "278645"); sheet.set("B2417", "Arial")
sheet.set("A2418", "278650"); sheet.set("B2418", "SecretInternalRadArrowhead5473s6187")
sheet.set("A2419", "278653"); sheet.set("B2419", "EQ")
sheet.set("A2420", "278656"); sheet.set("B2420", "Arial")
sheet.set("A2421", "278661"); sheet.set("B2421", "SecretInternalTypePreviewgArrowhead5478765182")
sheet.set("A2422", "278664"); sheet.set("B2422", "C:\\pf_root\\9.0\\Data\\Platform\\Metric\\Library\\Annotations\\")
sheet.set("A2423", "278747"); sheet.set("B2423", "Filled Elevation Target Ä")
sheet.set("A2424", "312570"); sheet.set("B2424", "EQ")
sheet.set("A2425", "312573"); sheet.set("B2425", "Arial")
sheet.set("A2426", "312578"); sheet.set("B2426", "SecretInternalLinAngArrowhead547r36186")
sheet.set("A2427", "312581"); sheet.set("B2427", "EQ")
sheet.set("A2428", "312584"); sheet.set("B2428", "Arial")
sheet.set("A2429", "312589"); sheet.set("B2429", "SecretInternalRadArrowhead5473s6187")
sheet.set("A2430", "312592"); sheet.set("B2430", "EQ")
sheet.set("A2431", "312595"); sheet.set("B2431", "Arial")
sheet.set("A2432", "312600"); sheet.set("B2432", "SecretInternalTypePreviewgArrowhead5478765182")
sheet.set("A2433", "312603"); sheet.set("B2433", "C:\\Documents and Settings\\egberte\\Deskt")
sheet.set("A2434", "312603"); sheet.set("B2434", "C:\\Documents and Settings\\egberte\\D")
sheet.set("A2435", "312588"); sheet.set("B2435", "te")
sheet.set("A2436", "312581"); sheet.set("B2436", "ngs\\egberte\\Desk")
sheet.set("A2437", "312577"); sheet.set("B2437", "Åyle")
sheet.set("A2438", "17089817"); sheet.set("B2438", "ÿÿ")
sheet.set("A2439", "312577"); sheet.set("B2439", "nA")
sheet.set("A2440", "17089817"); sheet.set("B2440", "Horiz")
sheet.set("A2441", "17089817"); sheet.set("B2441", "Slo")
sheet.set("A2442", "302291"); sheet.set("B2442", "EQ")
sheet.set("A2443", "302294"); sheet.set("B2443", "Arial")
sheet.set("A2444", "302299"); sheet.set("B2444", "SecretInternalLinAngArrowhead547r36186")
sheet.set("A2445", "302302"); sheet.set("B2445", "EQ")
sheet.set("A2446", "302305"); sheet.set("B2446", "Arial")
sheet.set("A2447", "302310"); sheet.set("B2447", "SecretInternalRadArrowhead5473s6187")
sheet.set("A2448", "302313"); sheet.set("B2448", "EQ")
sheet.set("A2449", "302316"); sheet.set("B2449", "Arial")
sheet.set("A2450", "302321"); sheet.set("B2450", "SecretInternalTypePreviewgArrowhead5478765182")
sheet.set("A2451", "302324"); sheet.set("B2451", "C:\\Documents and Settings\\All Users\\Application Data\\Autodesk\\RAC 2009\\Metric Library\\Detail Components\\Div 03-Concrete\\03400-Precast Concrete\\03410-Plant-Precast Structural Concrete\\")
sheet.set("A2452", "302339"); sheet.set("B2452", "Center (Front/Back)")
sheet.set("A2453", "302341"); sheet.set("B2453", "Left")
sheet.set("A2454", "302384"); sheet.set("B2454", "Wood - Finish")
sheet.set("A2455", "302511"); sheet.set("B2455", "Right")
sheet.set("A2456", "302513"); sheet.set("B2456", "Width")
sheet.set("A2457", "302525"); sheet.set("B2457", "Core Offset")
sheet.set("A2458", "302527"); sheet.set("B2458", "Top")
sheet.set("A2459", "302528"); sheet.set("B2459", "Number Of Cores")
sheet.set("A2460", "302531"); sheet.set("B2460", "Core Rep*")
sheet.set("A2461", "302586"); sheet.set("B2461", "Core Rep")
sheet.set("A2462", "302593"); sheet.set("B2462", "?à")
sheet.set("A2463", "312856"); sheet.set("B2463", "EQ")
sheet.set("A2464", "312859"); sheet.set("B2464", "Arial")
sheet.set("A2465", "312864"); sheet.set("B2465", "SecretInternalLinAngArrowhead547r36186")
sheet.set("A2466", "312867"); sheet.set("B2466", "EQ")
sheet.set("A2467", "312870"); sheet.set("B2467", "Arial")
sheet.set("A2468", "312875"); sheet.set("B2468", "SecretInternalRadArrowhead5473s6187")
sheet.set("A2469", "312878"); sheet.set("B2469", "EQ")
sheet.set("A2470", "312881"); sheet.set("B2470", "Arial")
sheet.set("A2471", "312886"); sheet.set("B2471", "SecretInternalTypePreviewgArrowhead5478765182")
sheet.set("A2472", "312889"); sheet.set("B2472", "C:\\DOCUME~1\\hansonje\\LOCALS~1\\Temp\\")
sheet.set("A2473", "285495"); sheet.set("B2473", "EQ")
sheet.set("A2474", "285498"); sheet.set("B2474", "Arial")
sheet.set("A2475", "285503"); sheet.set("B2475", "SecretInternalLinAngArrowhead547r36186")
sheet.set("A2476", "285506"); sheet.set("B2476", "EQ")
sheet.set("A2477", "285509"); sheet.set("B2477", "Arial")
sheet.set("A2478", "285514"); sheet.set("B2478", "SecretInternalRadArrowhead5473s6187")
sheet.set("A2479", "285517"); sheet.set("B2479", "EQ")
sheet.set("A2480", "285520"); sheet.set("B2480", "Arial")
sheet.set("A2481", "285525"); sheet.set("B2481", "SecretInternalTypePreviewgArrowhead5478765182")
sheet.set("A2482", "285528"); sheet.set("B2482", "F:\\pf_root\\dev\\Data\\Metric\\Library\\Furniture\\")
sheet.set("A2483", "285570"); sheet.set("B2483", "Curtain Wall 1")
sheet.set("A2484", "285580"); sheet.set("B2484", "ÿ\"")
sheet.set("A2485", "285591"); sheet.set("B2485", "View 1")
sheet.set("A2486", "285675"); sheet.set("B2486", "Center (Left/Right)")
sheet.set("A2487", "285676"); sheet.set("B2487", "Center (Front/Back)")
sheet.set("A2488", "285702"); sheet.set("B2488", "ÿD")
sheet.set("A2489", "285722"); sheet.set("B2489", "Drawer Edge")
sheet.set("A2490", "285725"); sheet.set("B2490", "ÿV")
sheet.set("A2491", "285740"); sheet.set("B2491", "ÿÆ")
sheet.set("A2492", "285742"); sheet.set("B2492", "Profile plane")
sheet.set("A2493", "285753"); sheet.set("B2493", "K@")
sheet.set("A2494", "285760"); sheet.set("B2494", "Pro")
sheet.set("A2495", "285760"); sheet.set("B2495", "nã")
sheet.set("A2496", "285760"); sheet.set("B2496", "{T")
sheet.set("A2497", "12517424"); sheet.set("B2497", "nã")
sheet.set("A2498", "285760"); sheet.set("B2498", "al")
sheet.set("A2499", "285918"); sheet.set("B2499", "Filled Elevation Target Ä")
sheet.set("A2500", "285924"); sheet.set("B2500", "6mm")
sheet.set("A2501", "286081"); sheet.set("B2501", "Top")
sheet.set("A2502", "286082"); sheet.set("B2502", "Right")
sheet.set("A2503", "286095"); sheet.set("B2503", "Left")
sheet.set("A2504", "286096"); sheet.set("B2504", "Bottom")
sheet.set("A2505", "286133"); sheet.set("B2505", "Ö@")
sheet.set("A2506", "303217"); sheet.set("B2506", "EQ")
sheet.set("A2507", "303220"); sheet.set("B2507", "Arial")
sheet.set("A2508", "303225"); sheet.set("B2508", "SecretInternalLinAngArrowhead54736k182")
sheet.set("A2509", "303228"); sheet.set("B2509", "EQ")
sheet.set("A2510", "303231"); sheet.set("B2510", "Arial")
sheet.set("A2511", "303236"); sheet.set("B2511", "SecretInternalRadArrowhead5473s6187")
sheet.set("A2512", "303239"); sheet.set("B2512", "EQ")
sheet.set("A2513", "303242"); sheet.set("B2513", "Arial")
sheet.set("A2514", "303247"); sheet.set("B2514", "SecretInternalTypePreviewgArrowhead5478765182")
sheet.set("A2515", "303250"); sheet.set("B2515", "C:\\Documents and Settings\\All Users\\Application Data\\Autodesk\\RAC 2009\\Metric Library\\Detail Components\\Div 07-Thermal and Moisture Protection\\07200-Thermal Protection\\07210-Building Insulation\\")
sheet.set("A2516", "303265"); sheet.set("B2516", "Bottom")
sheet.set("A2517", "303267"); sheet.set("B2517", "Center (Left/Right)")
sheet.set("A2518", "303316"); sheet.set("B2518", "Concrete")
sheet.set("A2519", "303334"); sheet.set("B2519", "Depth1")
sheet.set("A2520", "290732"); sheet.set("B2520", "EQ")
sheet.set("A2521", "290735"); sheet.set("B2521", "Arial")
sheet.set("A2522", "290740"); sheet.set("B2522", "SecretInternalLinAngArrowhead547r36186")
sheet.set("A2523", "290743"); sheet.set("B2523", "EQ")
sheet.set("A2524", "290746"); sheet.set("B2524", "Arial")
sheet.set("A2525", "290751"); sheet.set("B2525", "SecretInternalRadArrowhead5473s6187")
sheet.set("A2526", "290754"); sheet.set("B2526", "EQ")
sheet.set("A2527", "290757"); sheet.set("B2527", "Arial")
sheet.set("A2528", "290762"); sheet.set("B2528", "SecretInternalTypePreviewgArrowhead5478765182")
sheet.set("A2529", "290765"); sheet.set("B2529", "\\\\manbsdsrv02\\docs\\bsd\\Architectural_Tutorials\\Revit_Architecture_2010_Tutorials\\Imperial Datasets\\08 - Adding Other Elements\\")
sheet.set("A2530", "290800"); sheet.set("B2530", "Center (Front/Back)")
sheet.set("A2531", "290802"); sheet.set("B2531", "Center (Left/Right)")
sheet.set("A2532", "290848"); sheet.set("B2532", "Top")
sheet.set("A2533", "290856"); sheet.set("B2533", "View 1")
sheet.set("A2534", "290896"); sheet.set("B2534", "Level Head - Upgrade")
sheet.set("A2535", "290909"); sheet.set("B2535", "Elevation 1")
sheet.set("A2536", "290954"); sheet.set("B2536", "Name")
sheet.set("A2537", "290979"); sheet.set("B2537", "Filled Elevation Target Ä")
sheet.set("A2538", "290985"); sheet.set("B2538", "1/4\"")
sheet.set("A2539", "290991"); sheet.set("B2539", "Handrail Radius")
sheet.set("A2540", "291018"); sheet.set("B2540", "return")
sheet.set("A2541", "291024"); sheet.set("B2541", "ÿ(")
sheet.set("A2542", "291026"); sheet.set("B2542", "Profile plane")
sheet.set("A2543", "291061"); sheet.set("B2543", "Profile plane")
sheet.set("A2544", "313153"); sheet.set("B2544", "EQ")
sheet.set("A2545", "313156"); sheet.set("B2545", "Arial")
sheet.set("A2546", "313161"); sheet.set("B2546", "SecretInternalLinAngArrowhead54736k182")
sheet.set("A2547", "313164"); sheet.set("B2547", "EQ")
sheet.set("A2548", "313167"); sheet.set("B2548", "Arial")
sheet.set("A2549", "313172"); sheet.set("B2549", "SecretInternalRadArrowhead5473618n4")
sheet.set("A2550", "313175"); sheet.set("B2550", "EQ")
sheet.set("A2551", "313178"); sheet.set("B2551", "Arial")
sheet.set("A2552", "313183"); sheet.set("B2552", "SecretInternalTypePreviewgArrowhead5478765182")
sheet.set("A2553", "313186"); sheet.set("B2553", "C:\\Users\\hansonje\\Desktop\\")
sheet.set("A2554", "313187"); sheet.set("B2554", "Arrow 30 Degree")
sheet.set("A2555", "313190"); sheet.set("B2555", "SecretInternalRadArrowhead5473s6187")
sheet.set("A2556", "313192"); sheet.set("B2556", "EQ")
sheet.set("A2557", "313208"); sheet.set("B2557", "???")
sheet.set("A2558", "313219"); sheet.set("B2558", "5 mm")
sheet.set("A2559", "313237"); sheet.set("B2559", "13 mm")
sheet.set("A2560", "313247"); sheet.set("B2560", "13 i mm")
sheet.set("A2561", "313270"); sheet.set("B2561", "3 mm")
sheet.set("A2562", "313294"); sheet.set("B2562", "8 i mm")
sheet.set("A2563", "275197"); sheet.set("B2563", "EQ")
sheet.set("A2564", "275200"); sheet.set("B2564", "Arial")
sheet.set("A2565", "275205"); sheet.set("B2565", "SecretInternalLinAngArrowhead54736k182")
sheet.set("A2566", "275208"); sheet.set("B2566", "EQ")
sheet.set("A2567", "275211"); sheet.set("B2567", "Arial")
sheet.set("A2568", "275216"); sheet.set("B2568", "SecretInternalRadArrowhead5473618n4")
sheet.set("A2569", "275219"); sheet.set("B2569", "EQ")
sheet.set("A2570", "275222"); sheet.set("B2570", "Arial")
sheet.set("A2571", "275227"); sheet.set("B2571", "SecretInternalTypePreviewgArrowhead5478765182")
sheet.set("A2572", "275230"); sheet.set("B2572", "D:\\PF_Root\\8.0\\data\\Metric\\Library\\Annotations\\")
sheet.set("A2573", "275279"); sheet.set("B2573", "Solid Black")
sheet.set("A2574", "296422"); sheet.set("B2574", "EQ")
sheet.set("A2575", "296425"); sheet.set("B2575", "Arial")
sheet.set("A2576", "296430"); sheet.set("B2576", "SecretInternalLinAngArrowhead547r36186")
sheet.set("A2577", "296433"); sheet.set("B2577", "EQ")
sheet.set("A2578", "296436"); sheet.set("B2578", "Arial")
sheet.set("A2579", "296441"); sheet.set("B2579", "SecretInternalRadArrowhead5473s6187")
sheet.set("A2580", "296444"); sheet.set("B2580", "EQ")
sheet.set("A2581", "296447"); sheet.set("B2581", "Arial")
sheet.set("A2582", "296452"); sheet.set("B2582", "SecretInternalTypePreviewgArrowhead5478765182")
sheet.set("A2583", "296455"); sheet.set("B2583", "C:\\Documents and Settings\\All Users\\Application Data\\Autodesk\\RAC 2009\\Metric Library\\Structural\\Framing\\Steel\\")
sheet.set("A2584", "296503"); sheet.set("B2584", "Center (Front/Back)")
sheet.set("A2585", "296505"); sheet.set("B2585", "Center (Left/Right)")
sheet.set("A2586", "296544"); sheet.set("B2586", "Member Left")
sheet.set("A2587", "296545"); sheet.set("B2587", "Member Right")
sheet.set("A2588", "296550"); sheet.set("B2588", "Top")
sheet.set("A2589", "296563"); sheet.set("B2589", "{3D}")
sheet.set("A2590", "296572"); sheet.set("B2590", "Left")
sheet.set("A2591", "296772"); sheet.set("B2591", "M_W-Wide Flange-Profile-Fine@")
sheet.set("A2592", "296790"); sheet.set("B2592", "M_W-Wide Flange-Profile-Fine")
sheet.set("A2593", "296792"); sheet.set("B2593", "ÿ2")
sheet.set("A2594", "296795"); sheet.set("B2594", "Profile plane")
sheet.set("A2595", "296798"); sheet.set("B2595", "ÿB")
sheet.set("A2596", "296801"); sheet.set("B2596", "Profile plane")
sheet.set("A2597", "296814"); sheet.set("B2597", "Sim")
sheet.set("A2598", "296829"); sheet.set("B2598", "U@")
sheet.set("A2599", "307769"); sheet.set("B2599", "Name")
sheet.set("A2600", "307794"); sheet.set("B2600", "Filled Elevation Target Ä")
sheet.set("A2601", "307800"); sheet.set("B2601", "1/4\"")
sheet.set("A2602", "302620"); sheet.set("B2602", "EQ")
sheet.set("A2603", "302623"); sheet.set("B2603", "Arial")
sheet.set("A2604", "302628"); sheet.set("B2604", "SecretInternalLinAngArrowhead547r36186")
sheet.set("A2605", "302631"); sheet.set("B2605", "EQ")
sheet.set("A2606", "302634"); sheet.set("B2606", "Arial")
sheet.set("A2607", "302639"); sheet.set("B2607", "SecretInternalRadArrowhead5473s6187")
sheet.set("A2608", "302642"); sheet.set("B2608", "EQ")
sheet.set("A2609", "302645"); sheet.set("B2609", "Arial")
sheet.set("A2610", "302650"); sheet.set("B2610", "SecretInternalTypePreviewgArrowhead5478765182")
sheet.set("A2611", "302653"); sheet.set("B2611", "C:\\Documents and Settings\\All Users\\Application Data\\Autodesk\\RAC 2009\\Metric Library\\Detail Components\\Div 07-Thermal and Moisture Protection\\07600-Flashing and Sheet Metal\\07645-Preformed Flashings\\")
sheet.set("A2612", "302668"); sheet.set("B2612", "Center (Front/Back)")
sheet.set("A2613", "302670"); sheet.set("B2613", "Center (Left/Right)")
sheet.set("A2614", "302833"); sheet.set("B2614", "Right")
sheet.set("A2615", "302858"); sheet.set("B2615", "M!")
sheet.set("A2616", "298579"); sheet.set("B2616", "EQ")
sheet.set("A2617", "298582"); sheet.set("B2617", "Arial")
sheet.set("A2618", "298587"); sheet.set("B2618", "SecretInternalLinAngArrowhead54736k182")
sheet.set("A2619", "298590"); sheet.set("B2619", "EQ")
sheet.set("A2620", "298593"); sheet.set("B2620", "Arial")
sheet.set("A2621", "298598"); sheet.set("B2621", "SecretInternalRadArrowhead5473618n4")
sheet.set("A2622", "298601"); sheet.set("B2622", "EQ")
sheet.set("A2623", "298604"); sheet.set("B2623", "Arial")
sheet.set("A2624", "298609"); sheet.set("B2624", "SecretInternalTypePreviewgArrowhead5478765182")
sheet.set("A2625", "298612"); sheet.set("B2625", "D:\\PF_Root\\dev\\Data\\Metric\\Library\\Structural\\Framing\\Concrete\\New Folder\\")
sheet.set("A2626", "298675"); sheet.set("B2626", "Center (Front/Back)")
sheet.set("A2627", "298677"); sheet.set("B2627", "Center (Left/Right)")
sheet.set("A2628", "298766"); sheet.set("B2628", "EQ")
sheet.set("A2629", "297069"); sheet.set("B2629", "EQ")
sheet.set("A2630", "297072"); sheet.set("B2630", "Arial")
sheet.set("A2631", "297077"); sheet.set("B2631", "SecretInternalLinAngArrowhead54736k182")
sheet.set("A2632", "297080"); sheet.set("B2632", "EQ")
sheet.set("A2633", "297083"); sheet.set("B2633", "Arial")
sheet.set("A2634", "297088"); sheet.set("B2634", "SecretInternalRadArrowhead5473618n4")
sheet.set("A2635", "297091"); sheet.set("B2635", "EQ")
sheet.set("A2636", "297094"); sheet.set("B2636", "Arial")
sheet.set("A2637", "297099"); sheet.set("B2637", "SecretInternalTypePreviewgArrowhead5478765182")
sheet.set("A2638", "297149"); sheet.set("B2638", "Solid Black")
sheet.set("A2639", "297190"); sheet.set("B2639", "all")
sheet.set("A2640", "275573"); sheet.set("B2640", "EQ")
sheet.set("A2641", "275576"); sheet.set("B2641", "Arial")
sheet.set("A2642", "275581"); sheet.set("B2642", "SecretInternalLinAngArrowhead54736k182")
sheet.set("A2643", "275584"); sheet.set("B2643", "EQ")
sheet.set("A2644", "275587"); sheet.set("B2644", "Arial")
sheet.set("A2645", "275592"); sheet.set("B2645", "SecretInternalRadArrowhead5473s6187")
sheet.set("A2646", "275595"); sheet.set("B2646", "EQ")
sheet.set("A2647", "275598"); sheet.set("B2647", "Arial")
sheet.set("A2648", "275603"); sheet.set("B2648", "SecretInternalTypePreviewgArrowhead5478765182")
sheet.set("A2649", "275606"); sheet.set("B2649", "C:\\pf_root\\dev\\Data\\Platform\\Metric\\Library\\Annotations\\Architectural\\")
sheet.set("A2650", "275626"); sheet.set("B2650", "Arrowhead 1")
sheet.set("A2651", "275743"); sheet.set("B2651", "System Panel")
sheet.set("A2652", "275745"); sheet.set("B2652", "Wall")
sheet.set("A2653", "312276"); sheet.set("B2653", "EQ")
sheet.set("A2654", "312279"); sheet.set("B2654", "Arial")
sheet.set("A2655", "312284"); sheet.set("B2655", "SecretInternalLinAngArrowhead547r36186")
sheet.set("A2656", "312287"); sheet.set("B2656", "EQ")
sheet.set("A2657", "312290"); sheet.set("B2657", "Arial")
sheet.set("A2658", "312295"); sheet.set("B2658", "SecretInternalRadArrowhead5473s6187")
sheet.set("A2659", "312298"); sheet.set("B2659", "EQ")
sheet.set("A2660", "312301"); sheet.set("B2660", "Arial")
sheet.set("A2661", "312306"); sheet.set("B2661", "SecretInternalTypePreviewgArrowhead5478765182")
sheet.set("A2662", "312309"); sheet.set("B2662", "C:\\DOCUME~1\\hansonje\\LOCALS~1\\Temp\\")
sheet.set("A2663", "312304"); sheet.set("B2663", "_base.f")
sheet.set("A2664", "291169"); sheet.set("B2664", "EQ")
sheet.set("A2665", "291172"); sheet.set("B2665", "Arial")
sheet.set("A2666", "291177"); sheet.set("B2666", "SecretInternalLinAngArrowhead54736k182")
sheet.set("A2667", "291180"); sheet.set("B2667", "EQ")
sheet.set("A2668", "291183"); sheet.set("B2668", "Arial")
sheet.set("A2669", "291188"); sheet.set("B2669", "SecretInternalRadArrowhead5473618n4")
sheet.set("A2670", "291191"); sheet.set("B2670", "EQ")
sheet.set("A2671", "291194"); sheet.set("B2671", "Arial")
sheet.set("A2672", "291199"); sheet.set("B2672", "SecretInternalTypePreviewgArrowhead5478765182")
sheet.set("A2673", "291202"); sheet.set("B2673", "C:\\pf_root\\9.0\\Data\\Platform\\Imperial\\Library\\Profiles\\Stairs\\")
sheet.set("A2674", "291268"); sheet.set("B2674", "Revealy")
sheet.set("A2675", "274972"); sheet.set("B2675", "EQ")
sheet.set("A2676", "274975"); sheet.set("B2676", "Arial")
sheet.set("A2677", "274980"); sheet.set("B2677", "SecretInternalLinAngArrowhead547r36186")
sheet.set("A2678", "274983"); sheet.set("B2678", "EQ")
sheet.set("A2679", "274986"); sheet.set("B2679", "Arial")
sheet.set("A2680", "274991"); sheet.set("B2680", "SecretInternalRadArrowhead5473s6187")
sheet.set("A2681", "274994"); sheet.set("B2681", "EQ")
sheet.set("A2682", "274997"); sheet.set("B2682", "Arial")
sheet.set("A2683", "275002"); sheet.set("B2683", "SecretInternalTypePreviewgArrowhead5478765182")
sheet.set("A2684", "275005"); sheet.set("B2684", "D:\\PF_Root\\8.0\\data\\Metric\\Library\\Detail Components\\Architectural\\")
sheet.set("A2685", "275023"); sheet.set("B2685", "Bottom")
sheet.set("A2686", "275025"); sheet.set("B2686", "Front")
sheet.set("A2687", "275074"); sheet.set("B2687", "Brick")
sheet.set("A2688", "275181"); sheet.set("B2688", "EQ")
sheet.set("A2689", "310620"); sheet.set("B2689", "EQ")
sheet.set("A2690", "310623"); sheet.set("B2690", "Arial")
sheet.set("A2691", "310628"); sheet.set("B2691", "SecretInternalLinAngArrowhead54736k182")
sheet.set("A2692", "310631"); sheet.set("B2692", "EQ")
sheet.set("A2693", "310634"); sheet.set("B2693", "Arial")
sheet.set("A2694", "310639"); sheet.set("B2694", "SecretInternalRadArrowhead5473618n4")
sheet.set("A2695", "310642"); sheet.set("B2695", "EQ")
sheet.set("A2696", "310645"); sheet.set("B2696", "Arial")
sheet.set("A2697", "310650"); sheet.set("B2697", "SecretInternalTypePreviewgArrowhead5478765182")
sheet.set("A2698", "310700"); sheet.set("B2698", "Solid Black")
sheet.set("A2699", "310741"); sheet.set("B2699", "all")
sheet.set("A2700", "284145"); sheet.set("B2700", "EQ")
sheet.set("A2701", "284148"); sheet.set("B2701", "Arial")
sheet.set("A2702", "284153"); sheet.set("B2702", "SecretInternalLinAngArrowhead54736k182")
sheet.set("A2703", "284156"); sheet.set("B2703", "EQ")
sheet.set("A2704", "284159"); sheet.set("B2704", "Arial")
sheet.set("A2705", "284164"); sheet.set("B2705", "SecretInternalRadArrowhead5473s6187")
sheet.set("A2706", "284167"); sheet.set("B2706", "EQ")
sheet.set("A2707", "284170"); sheet.set("B2707", "Arial")
sheet.set("A2708", "284175"); sheet.set("B2708", "SecretInternalTypePreviewgArrowhead5478765182")
sheet.set("A2709", "284178"); sheet.set("B2709", "C:\\pf_root\\dev\\Data\\Platform\\Imperial\\Library\\Annotations\\")
sheet.set("A2710", "284249"); sheet.set("B2710", "Filled Elevation Target Ä")
sheet.set("A2711", "300180"); sheet.set("B2711", "EQ")
sheet.set("A2712", "300183"); sheet.set("B2712", "Arial")
sheet.set("A2713", "300188"); sheet.set("B2713", "SecretInternalLinAngArrowhead547r36186")
sheet.set("A2714", "300191"); sheet.set("B2714", "EQ")
sheet.set("A2715", "300194"); sheet.set("B2715", "Arial")
sheet.set("A2716", "300199"); sheet.set("B2716", "SecretInternalRadArrowhead5473s6187")
sheet.set("A2717", "300202"); sheet.set("B2717", "EQ")
sheet.set("A2718", "300205"); sheet.set("B2718", "Arial")
sheet.set("A2719", "300210"); sheet.set("B2719", "SecretInternalTypePreviewgArrowhead5478765182")
sheet.set("A2720", "300213"); sheet.set("B2720", "C:\\Documents and Settings\\All Users\\Application Data\\Autodesk\\RAC 2009\\Imperial Library\\Detail Components\\Structural\\Concrete\\")
sheet.set("A2721", "300228"); sheet.set("B2721", "Center (Front/Back)")
sheet.set("A2722", "300230"); sheet.set("B2722", "Center (Left/Right)")
sheet.set("A2723", "300300"); sheet.set("B2723", "Revealy")
sheet.set("A2724", "276329"); sheet.set("B2724", "EQ")
sheet.set("A2725", "276332"); sheet.set("B2725", "Arial")
sheet.set("A2726", "276337"); sheet.set("B2726", "SecretInternalLinAngArrowhead54736k182")
sheet.set("A2727", "276340"); sheet.set("B2727", "EQ")
sheet.set("A2728", "276343"); sheet.set("B2728", "Arial")
sheet.set("A2729", "276348"); sheet.set("B2729", "SecretInternalRadArrowhead5473s6187")
sheet.set("A2730", "276351"); sheet.set("B2730", "EQ")
sheet.set("A2731", "276354"); sheet.set("B2731", "Arial")
sheet.set("A2732", "276359"); sheet.set("B2732", "SecretInternalTypePreviewgArrowhead5478765182")
sheet.set("A2733", "276362"); sheet.set("B2733", "C:\\pf_root\\9.0\\Data\\Platform\\Metric\\Library\\Annotations\\Architectural\\")
sheet.set("A2734", "276386"); sheet.set("B2734", "Arrowhead 1")
sheet.set("A2735", "280616"); sheet.set("B2735", "EQ")
sheet.set("A2736", "280619"); sheet.set("B2736", "Arial")
sheet.set("A2737", "280624"); sheet.set("B2737", "SecretInternalLinAngArrowhead547r36186")
sheet.set("A2738", "280627"); sheet.set("B2738", "EQ")
sheet.set("A2739", "280630"); sheet.set("B2739", "Arial")
sheet.set("A2740", "280635"); sheet.set("B2740", "SecretInternalRadArrowhead5473618n4")
sheet.set("A2741", "280638"); sheet.set("B2741", "EQ")
sheet.set("A2742", "280641"); sheet.set("B2742", "Arial")
sheet.set("A2743", "280646"); sheet.set("B2743", "SecretInternalTypePreviewgArrowhead5478765182")
sheet.set("A2744", "280649"); sheet.set("B2744", "C:\\pf_root\\9.0\\Data\\Platform\\Metric\\Library\\Profiles\\Stairs\\")
sheet.set("A2745", "280714"); sheet.set("B2745", "Revealy")
sheet.set("A2746", "289645"); sheet.set("B2746", "EQ")
sheet.set("A2747", "289648"); sheet.set("B2747", "Arial")
sheet.set("A2748", "289653"); sheet.set("B2748", "SecretInternalLinAngArrowhead547r36186")
sheet.set("A2749", "289656"); sheet.set("B2749", "EQ")
sheet.set("A2750", "289659"); sheet.set("B2750", "Arial")
sheet.set("A2751", "289664"); sheet.set("B2751", "SecretInternalRadArrowhead5473s6187")
sheet.set("A2752", "289667"); sheet.set("B2752", "EQ")
sheet.set("A2753", "289670"); sheet.set("B2753", "Arial")
sheet.set("A2754", "289675"); sheet.set("B2754", "SecretInternalTypePreviewgArrowhead5478765182")
sheet.set("A2755", "289678"); sheet.set("B2755", "\\\\manbsdsrv02\\docs\\bsd\\Architectural_Tutorials\\Revit_Architecture_2010_Tutorials\\Imperial Datasets\\08 - Adding Other Elements\\")
sheet.set("A2756", "289713"); sheet.set("B2756", "Center (Front/Back)")
sheet.set("A2757", "289715"); sheet.set("B2757", "Center (Left/Right)")
sheet.set("A2758", "289761"); sheet.set("B2758", "Top")
sheet.set("A2759", "289769"); sheet.set("B2759", "View 1")
sheet.set("A2760", "289809"); sheet.set("B2760", "Level Head - Upgrade")
sheet.set("A2761", "289822"); sheet.set("B2761", "Elevation 1")
sheet.set("A2762", "289867"); sheet.set("B2762", "Name")
sheet.set("A2763", "289892"); sheet.set("B2763", "Filled Elevation Target Ä")
sheet.set("A2764", "289898"); sheet.set("B2764", "1/4\"")
sheet.set("A2765", "289904"); sheet.set("B2765", "Handrail Radius")
sheet.set("A2766", "289910"); sheet.set("B2766", "return")
sheet.set("A2767", "289916"); sheet.set("B2767", "ÿ\\")
sheet.set("A2768", "289919"); sheet.set("B2768", "Profile plane")
sheet.set("A2769", "289959"); sheet.set("B2769", "ÿ@")
sheet.set("A2770", "289962"); sheet.set("B2770", "Profile plane")
sheet.set("A2771", "289992"); sheet.set("B2771", "ÿ<")
sheet.set("A2772", "289999"); sheet.set("B2772", "W@")
sheet.set("A2773", "290005"); sheet.set("B2773", "*@")
sheet.set("A2774", "290009"); sheet.set("B2774", "transition")
sheet.set("A2775", "290014"); sheet.set("B2775", "*@")
sheet.set("A2776", "290015"); sheet.set("B2776", "*@")
sheet.set("A2777", "290016"); sheet.set("B2777", "*@")
sheet.set("A2778", "290017"); sheet.set("B2778", "*@")
sheet.set("A2779", "290018"); sheet.set("B2779", "*@")
sheet.set("A2780", "290019"); sheet.set("B2780", "g@")
sheet.set("A2781", "290024"); sheet.set("B2781", "*@")
sheet.set("A2782", "290025"); sheet.set("B2782", "Profile plane")
sheet.set("A2783", "290026"); sheet.set("B2783", "*@")
sheet.set("A2784", "290029"); sheet.set("B2784", "*@")
sheet.set("A2785", "290035"); sheet.set("B2785", "Ý@")
sheet.set("A2786", "290036"); sheet.set("B2786", "*@")
sheet.set("A2787", "290037"); sheet.set("B2787", "*@")
sheet.set("A2788", "290038"); sheet.set("B2788", "*@")
sheet.set("A2789", "290039"); sheet.set("B2789", "ß@")
sheet.set("A2790", "290040"); sheet.set("B2790", "*@")
sheet.set("A2791", "290041"); sheet.set("B2791", "*@")
sheet.set("A2792", "290042"); sheet.set("B2792", "ÿ.")
sheet.set("A2793", "278826"); sheet.set("B2793", "EQ")
sheet.set("A2794", "278829"); sheet.set("B2794", "Arial")
sheet.set("A2795", "278834"); sheet.set("B2795", "SecretInternalLinAngArrowhead54736k182")
sheet.set("A2796", "278837"); sheet.set("B2796", "EQ")
sheet.set("A2797", "278840"); sheet.set("B2797", "Arial")
sheet.set("A2798", "278845"); sheet.set("B2798", "SecretInternalRadArrowhead5473s6187")
sheet.set("A2799", "278848"); sheet.set("B2799", "EQ")
sheet.set("A2800", "278851"); sheet.set("B2800", "Arial")
sheet.set("A2801", "278856"); sheet.set("B2801", "SecretInternalTypePreviewgArrowhead5478765182")
sheet.set("A2802", "278859"); sheet.set("B2802", "C:\\pf_root\\9.0\\Data\\Platform\\Metric\\Library\\Annotations\\")
sheet.set("A2803", "278875"); sheet.set("B2803", "4mm")
sheet.set("A2804", "291382"); sheet.set("B2804", "EQ")
sheet.set("A2805", "291385"); sheet.set("B2805", "Arial")
sheet.set("A2806", "291390"); sheet.set("B2806", "SecretInternalLinAngArrowhead547r36186")
sheet.set("A2807", "291393"); sheet.set("B2807", "EQ")
sheet.set("A2808", "291396"); sheet.set("B2808", "Arial")
sheet.set("A2809", "291401"); sheet.set("B2809", "SecretInternalRadArrowhead5473s6187")
sheet.set("A2810", "291404"); sheet.set("B2810", "EQ")
sheet.set("A2811", "291407"); sheet.set("B2811", "Arial")
sheet.set("A2812", "291412"); sheet.set("B2812", "SecretInternalTypePreviewgArrowhead5478765182")
sheet.set("A2813", "291415"); sheet.set("B2813", "C:\\pf_root\\9.0\\Data\\Platform\\Imperial\\Library\\Architectural\\Balusters\\")
sheet.set("A2814", "291427"); sheet.set("B2814", "Ref. Level")
sheet.set("A2815", "291452"); sheet.set("B2815", "Center (Front/Back)")
sheet.set("A2816", "291454"); sheet.set("B2816", "Center (Left/Right)")
sheet.set("A2817", "291500"); sheet.set("B2817", "Top")
sheet.set("A2818", "291508"); sheet.set("B2818", "View 1")
sheet.set("A2819", "291513"); sheet.set("B2819", "Top Cut Angle")
sheet.set("A2820", "291515"); sheet.set("B2820", "j@")
sheet.set("A2821", "291526"); sheet.set("B2821", "ÿ\"")
sheet.set("A2822", "291527"); sheet.set("B2822", "ÿr")
sheet.set("A2823", "291540"); sheet.set("B2823", "ÿl")
sheet.set("A2824", "291572"); sheet.set("B2824", "Level Head - Upgrade")
sheet.set("A2825", "291585"); sheet.set("B2825", "Elevation 1")
sheet.set("A2826", "291630"); sheet.set("B2826", "Name")
sheet.set("A2827", "291655"); sheet.set("B2827", "Filled Elevation Target Ä")
sheet.set("A2828", "291661"); sheet.set("B2828", "1/4\"")
sheet.set("A2829", "291665"); sheet.set("B2829", "Bottom Cut Angle")
sheet.set("A2830", "277460"); sheet.set("B2830", "EQ")
sheet.set("A2831", "277463"); sheet.set("B2831", "Arial")
sheet.set("A2832", "277468"); sheet.set("B2832", "SecretInternalLinAngArrowhead54736k182")
sheet.set("A2833", "277471"); sheet.set("B2833", "EQ")
sheet.set("A2834", "277474"); sheet.set("B2834", "Arial")
sheet.set("A2835", "277479"); sheet.set("B2835", "SecretInternalRadArrowhead5473618n4")
sheet.set("A2836", "277482"); sheet.set("B2836", "EQ")
sheet.set("A2837", "277485"); sheet.set("B2837", "Arial")
sheet.set("A2838", "277490"); sheet.set("B2838", "SecretInternalTypePreviewgArrowhead5478765182")
sheet.set("A2839", "277493"); sheet.set("B2839", "C:\\pf_root\\9.0\\Data\\Platform\\Metric\\Library\\Annotations\\")
sheet.set("A2840", "277506"); sheet.set("B2840", "Baseline")
sheet.set("A2841", "277542"); sheet.set("B2841", "A101")
sheet.set("A2842", "277575"); sheet.set("B2842", "Ref")
sheet.set("A2843", "284836"); sheet.set("B2843", "EQ")
sheet.set("A2844", "284839"); sheet.set("B2844", "Arial")
sheet.set("A2845", "284844"); sheet.set("B2845", "SecretInternalLinAngArrowhead547r36186")
sheet.set("A2846", "284847"); sheet.set("B2846", "EQ")
sheet.set("A2847", "284850"); sheet.set("B2847", "Arial")
sheet.set("A2848", "284855"); sheet.set("B2848", "SecretInternalRadArrowhead5473s6187")
sheet.set("A2849", "284858"); sheet.set("B2849", "EQ")
sheet.set("A2850", "284861"); sheet.set("B2850", "Arial")
sheet.set("A2851", "284866"); sheet.set("B2851", "SecretInternalTypePreviewgArrowhead5478765182")
sheet.set("A2852", "284869"); sheet.set("B2852", "C:\\pf_root\\dev\\Data\\Platform\\Metric\\Library\\Structural\\Framing\\Steel\\")
sheet.set("A2853", "284919"); sheet.set("B2853", "Center (Front/Back)")
sheet.set("A2854", "284921"); sheet.set("B2854", "Center (Left/Right)")
sheet.set("A2855", "284960"); sheet.set("B2855", "Member Left")
sheet.set("A2856", "284961"); sheet.set("B2856", "Member Right")
sheet.set("A2857", "284966"); sheet.set("B2857", "Top")
sheet.set("A2858", "284979"); sheet.set("B2858", "{3D}")
sheet.set("A2859", "284988"); sheet.set("B2859", "Left")
sheet.set("A2860", "284989"); sheet.set("B2860", "Right")
sheet.set("A2861", "285030"); sheet.set("B2861", "Level Head - Upgrade")
sheet.set("A2862", "285043"); sheet.set("B2862", "Elevation 1")
sheet.set("A2863", "285088"); sheet.set("B2863", "Name")
sheet.set("A2864", "285113"); sheet.set("B2864", "Filled Elevation Target Ä")
sheet.set("A2865", "285119"); sheet.set("B2865", "6.35 mm")
sheet.set("A2866", "285175"); sheet.set("B2866", "M_W-Wide Flange-Profile-Medium@")
sheet.set("A2867", "285192"); sheet.set("B2867", "M_W-Wide Flange-Profile-Medium")
sheet.set("A2868", "285194"); sheet.set("B2868", "M_W-Wide Flange-Profile-Fine@")
sheet.set("A2869", "285212"); sheet.set("B2869", "M_W-Wide Flange-Profile-Fine")
sheet.set("A2870", "285214"); sheet.set("B2870", "ÿB")
sheet.set("A2871", "285217"); sheet.set("B2871", "Profile plane")
sheet.set("A2872", "285220"); sheet.set("B2872", "ÿ2")
sheet.set("A2873", "285223"); sheet.set("B2873", "Profile plane")
sheet.set("A2874", "285236"); sheet.set("B2874", "Sim")
sheet.set("A2875", "285260"); sheet.set("B2875", "EQ")
sheet.set("A2876", "313487"); sheet.set("B2876", "EQ")
sheet.set("A2877", "313490"); sheet.set("B2877", "Arial")
sheet.set("A2878", "313495"); sheet.set("B2878", "SecretInternalLinAngArrowhead54736k182")
sheet.set("A2879", "313498"); sheet.set("B2879", "EQ")
sheet.set("A2880", "313501"); sheet.set("B2880", "Arial")
sheet.set("A2881", "313506"); sheet.set("B2881", "SecretInternalRadArrowhead5473618n4")
sheet.set("A2882", "313509"); sheet.set("B2882", "EQ")
sheet.set("A2883", "313512"); sheet.set("B2883", "Arial")
sheet.set("A2884", "313517"); sheet.set("B2884", "SecretInternalTypePreviewgArrowhead5478765182")
sheet.set("A2885", "313542"); sheet.set("B2885", "???")
sheet.set("A2886", "313553"); sheet.set("B2886", "5 mm")
sheet.set("A2887", "313571"); sheet.set("B2887", "13 mm")
sheet.set("A2888", "313581"); sheet.set("B2888", "13 i mm")
sheet.set("A2889", "313604"); sheet.set("B2889", "3 mm")
sheet.set("A2890", "313629"); sheet.set("B2890", "Arial")
sheet.set("A2891", "289437"); sheet.set("B2891", "EQ")
sheet.set("A2892", "289440"); sheet.set("B2892", "Arial")
sheet.set("A2893", "289445"); sheet.set("B2893", "SecretInternalLinAngArrowhead54736k182")
sheet.set("A2894", "289448"); sheet.set("B2894", "EQ")
sheet.set("A2895", "289451"); sheet.set("B2895", "Arial")
sheet.set("A2896", "289456"); sheet.set("B2896", "SecretInternalRadArrowhead5473618n4")
sheet.set("A2897", "289459"); sheet.set("B2897", "EQ")
sheet.set("A2898", "289462"); sheet.set("B2898", "Arial")
sheet.set("A2899", "289467"); sheet.set("B2899", "SecretInternalTypePreviewgArrowhead5478765182")
sheet.set("A2900", "289470"); sheet.set("B2900", "C:\\pf_root\\9.0\\Data\\Platform\\Imperial\\Library\\Profiles\\Stairs\\")
sheet.set("A2901", "289534"); sheet.set("B2901", "Revealy")
sheet.set("A2902", "300608"); sheet.set("B2902", "EQ")
sheet.set("A2903", "300611"); sheet.set("B2903", "Arial")
sheet.set("A2904", "300616"); sheet.set("B2904", "SecretInternalLinAngArrowhead54736k182")
sheet.set("A2905", "300619"); sheet.set("B2905", "EQ")
sheet.set("A2906", "300622"); sheet.set("B2906", "Arial")
sheet.set("A2907", "300627"); sheet.set("B2907", "SecretInternalRadArrowhead5473s6187")
sheet.set("A2908", "300630"); sheet.set("B2908", "EQ")
sheet.set("A2909", "300633"); sheet.set("B2909", "Arial")
sheet.set("A2910", "300638"); sheet.set("B2910", "SecretInternalTypePreviewgArrowhead5478765182")
sheet.set("A2911", "300641"); sheet.set("B2911", "C:\\pf_root\\9.0\\Data\\Platform\\Imperial\\Library\\Annotations\\")
sheet.set("A2912", "300666"); sheet.set("B2912", "Datum Level 1")
sheet.set("A2913", "300704"); sheet.set("B2913", "SIM")
sheet.set("A2914", "302945"); sheet.set("B2914", "EQ")
sheet.set("A2915", "302948"); sheet.set("B2915", "Arial")
sheet.set("A2916", "302953"); sheet.set("B2916", "SecretInternalLinAngArrowhead547r36186")
sheet.set("A2917", "302956"); sheet.set("B2917", "EQ")
sheet.set("A2918", "302959"); sheet.set("B2918", "Arial")
sheet.set("A2919", "302964"); sheet.set("B2919", "SecretInternalRadArrowhead5473s6187")
sheet.set("A2920", "302967"); sheet.set("B2920", "EQ")
sheet.set("A2921", "302970"); sheet.set("B2921", "Arial")
sheet.set("A2922", "302975"); sheet.set("B2922", "SecretInternalTypePreviewgArrowhead5478765182")
sheet.set("A2923", "302978"); sheet.set("B2923", "C:\\Documents and Settings\\All Users\\Application Data\\Autodesk\\RAC 2009\\Imperial Library\\Detail Components\\Div 07-Thermal and Moisture Protection\\072100-Thermal Insulation\\072200-Roof and Deck Insulation\\")
sheet.set("A2924", "302993"); sheet.set("B2924", "Center (Front/Back)")
sheet.set("A2925", "302995"); sheet.set("B2925", "Center (Left/Right)")
sheet.set("A2926", "303097"); sheet.set("B2926", "Revealy")
sheet.set("A2927", "292253"); sheet.set("B2927", "EQ")
sheet.set("A2928", "292256"); sheet.set("B2928", "Arial")
sheet.set("A2929", "292261"); sheet.set("B2929", "SecretInternalLinAngArrowhead547r36186")
sheet.set("A2930", "292264"); sheet.set("B2930", "EQ")
sheet.set("A2931", "292267"); sheet.set("B2931", "Arial")
sheet.set("A2932", "292272"); sheet.set("B2932", "SecretInternalRadArrowhead5473s6187")
sheet.set("A2933", "292275"); sheet.set("B2933", "EQ")
sheet.set("A2934", "292278"); sheet.set("B2934", "Arial")
sheet.set("A2935", "292283"); sheet.set("B2935", "SecretInternalTypePreviewgArrowhead5478765182")
sheet.set("A2936", "292286"); sheet.set("B2936", "C:\\Documents and Settings\\All Users\\Application Data\\Autodesk\\RAC 2009\\Metric Library\\Furniture\\")
sheet.set("A2937", "292321"); sheet.set("B2937", "Center (Front/Back)")
sheet.set("A2938", "292323"); sheet.set("B2938", "Center (Left/Right)")
sheet.set("A2939", "292324"); sheet.set("B2939", "View 1")
sheet.set("A2940", "292345"); sheet.set("B2940", "YÀ")
sheet.set("A2941", "292361"); sheet.set("B2941", "ÿ\"")
sheet.set("A2942", "292382"); sheet.set("B2942", "ÿ ")
sheet.set("A2943", "292388"); sheet.set("B2943", "ÿ@")
sheet.set("A2944", "292393"); sheet.set("B2944", "ÿ@")
sheet.set("A2945", "292402"); sheet.set("B2945", "ÿ@")
sheet.set("A2946", "292437"); sheet.set("B2946", "ÿ\"")
sheet.set("A2947", "292453"); sheet.set("B2947", "ÿ@")
sheet.set("A2948", "292525"); sheet.set("B2948", "Level Head - Upgrade")
sheet.set("A2949", "292538"); sheet.set("B2949", "Elevation 1")
sheet.set("A2950", "292583"); sheet.set("B2950", "Name")
sheet.set("A2951", "292608"); sheet.set("B2951", "Filled Elevation Target Ä")
sheet.set("A2952", "292614"); sheet.set("B2952", "6.35 mm")
sheet.set("A2953", "292685"); sheet.set("B2953", "ÿæ")
sheet.set("A2954", "292686"); sheet.set("B2954", "Radius")
sheet.set("A2955", "292690"); sheet.set("B2955", "Array Group 1")
sheet.set("A2956", "292720"); sheet.set("B2956", "M_Chair-Breuer-")
sheet.set("A2957", "288135"); sheet.set("B2957", "EQ")
sheet.set("A2958", "288138"); sheet.set("B2958", "Arial")
sheet.set("A2959", "288143"); sheet.set("B2959", "SecretInternalLinAngArrowhead547r36186")
sheet.set("A2960", "288146"); sheet.set("B2960", "EQ")
sheet.set("A2961", "288149"); sheet.set("B2961", "Arial")
sheet.set("A2962", "288154"); sheet.set("B2962", "SecretInternalRadArrowhead5473s6187")
sheet.set("A2963", "288157"); sheet.set("B2963", "EQ")
sheet.set("A2964", "288160"); sheet.set("B2964", "Arial")
sheet.set("A2965", "288165"); sheet.set("B2965", "SecretInternalTypePreviewgArrowhead5478765182")
sheet.set("A2966", "288168"); sheet.set("B2966", "C:\\Documents and Settings\\All Users\\Application Data\\Autodesk\\RAC 2009\\Metric Library\\Structural\\Columns\\Concrete\\")
sheet.set("A2967", "288178"); sheet.set("B2967", "Lower Ref. Level")
sheet.set("A2968", "288187"); sheet.set("B2968", "Upper Ref Level")
sheet.set("A2969", "288204"); sheet.set("B2969", "Center (Front/Back)")
sheet.set("A2970", "288206"); sheet.set("B2970", "Center (Left/Right)")
sheet.set("A2971", "288213"); sheet.set("B2971", "ÿ*")
sheet.set("A2972", "288257"); sheet.set("B2972", "ÿ`")
sheet.set("A2973", "288271"); sheet.set("B2973", "{3D}")
sheet.set("A2974", "288319"); sheet.set("B2974", "Level Head - Upgrade")
sheet.set("A2975", "288332"); sheet.set("B2975", "Elevation 1")
sheet.set("A2976", "288377"); sheet.set("B2976", "Name")
sheet.set("A2977", "288402"); sheet.set("B2977", "Filled Elevation Target Ä")
sheet.set("A2978", "288408"); sheet.set("B2978", "6.35 mm")
sheet.set("A2979", "301412"); sheet.set("B2979", "EQ")
sheet.set("A2980", "301415"); sheet.set("B2980", "Arial")
sheet.set("A2981", "301420"); sheet.set("B2981", "SecretInternalLinAngArrowhead54736k182")
sheet.set("A2982", "301423"); sheet.set("B2982", "EQ")
sheet.set("A2983", "301426"); sheet.set("B2983", "Arial")
sheet.set("A2984", "301431"); sheet.set("B2984", "SecretInternalRadArrowhead5473618n4")
sheet.set("A2985", "301434"); sheet.set("B2985", "EQ")
sheet.set("A2986", "301437"); sheet.set("B2986", "Arial")
sheet.set("A2987", "301442"); sheet.set("B2987", "SecretInternalTypePreviewgArrowhead5478765182")
sheet.set("A2988", "301445"); sheet.set("B2988", "C:\\pf_root\\9.0\\Data\\Platform\\Imperial\\Library\\Annotations\\")
sheet.set("A2989", "1211031955"); sheet.set("B2989", "?t")
sheet.set("A2990", "1211031955"); sheet.set("B2990", "ÎH")
sheet.set("A2991", "1829175699"); sheet.set("B2991", "ruc")
sheet.set("A2992", "290137"); sheet.set("B2992", "EQ")
sheet.set("A2993", "290140"); sheet.set("B2993", "Arial")
sheet.set("A2994", "290145"); sheet.set("B2994", "SecretInternalLinAngArrowhead54736k182")
sheet.set("A2995", "290148"); sheet.set("B2995", "EQ")
sheet.set("A2996", "290151"); sheet.set("B2996", "Arial")
sheet.set("A2997", "290156"); sheet.set("B2997", "SecretInternalRadArrowhead5473618n4")
sheet.set("A2998", "290159"); sheet.set("B2998", "EQ")
sheet.set("A2999", "290162"); sheet.set("B2999", "Arial")
sheet.set("A3000", "290167"); sheet.set("B3000", "SecretInternalTypePreviewgArrowhead5478765182")
sheet.set("A3001", "290217"); sheet.set("B3001", "Solid Black")
sheet.set("A3002", "290258"); sheet.set("B3002", "all")
sheet.set("A3003", "301808"); sheet.set("B3003", "EQ")
sheet.set("A3004", "301811"); sheet.set("B3004", "Arial")
sheet.set("A3005", "301816"); sheet.set("B3005", "SecretInternalLinAngArrowhead54736k182")
sheet.set("A3006", "301819"); sheet.set("B3006", "EQ")
sheet.set("A3007", "301822"); sheet.set("B3007", "Arial")
sheet.set("A3008", "301827"); sheet.set("B3008", "SecretInternalRadArrowhead5473s6187")
sheet.set("A3009", "301830"); sheet.set("B3009", "EQ")
sheet.set("A3010", "301833"); sheet.set("B3010", "Arial")
sheet.set("A3011", "301838"); sheet.set("B3011", "SecretInternalTypePreviewgArrowhead5478765182")
sheet.set("A3012", "301841"); sheet.set("B3012", "C:\\Documents and Settings\\All Users\\Application Data\\Autodesk\\RAC 2009\\Metric Library\\Detail Components\\Div 01-General\\")
sheet.set("A3013", "301856"); sheet.set("B3013", "Break Line")
sheet.set("A3014", "301858"); sheet.set("B3014", "Center (Left/Right)")
sheet.set("A3015", "305583"); sheet.set("B3015", "EQ")
sheet.set("A3016", "305586"); sheet.set("B3016", "Arial")
sheet.set("A3017", "305591"); sheet.set("B3017", "SecretInternalLinAngArrowhead547r36186")
sheet.set("A3018", "305594"); sheet.set("B3018", "EQ")
sheet.set("A3019", "305597"); sheet.set("B3019", "Arial")
sheet.set("A3020", "305602"); sheet.set("B3020", "SecretInternalRadArrowhead5473s6187")
sheet.set("A3021", "305605"); sheet.set("B3021", "EQ")
sheet.set("A3022", "305608"); sheet.set("B3022", "Arial")
sheet.set("A3023", "305613"); sheet.set("B3023", "SecretInternalTypePreviewgArrowhead5478765182")
sheet.set("A3024", "305616"); sheet.set("B3024", "C:\\Documents and Settings\\campbes\\Desktop\\")
sheet.set("A3025", "305626"); sheet.set("B3025", "Ref. Level")
sheet.set("A3026", "305651"); sheet.set("B3026", "Center F/B")
sheet.set("A3027", "305653"); sheet.set("B3027", "Center L/R")
sheet.set("A3028", "305660"); sheet.set("B3028", "{3D}")
sheet.set("A3029", "305703"); sheet.set("B3029", "ÿG")
sheet.set("A3030", "305704"); sheet.set("B3030", "ÿà")
sheet.set("A3031", "305705"); sheet.set("B3031", "ÿà")
sheet.set("A3032", "305706"); sheet.set("B3032", "ÿà")
sheet.set("A3033", "305745"); sheet.set("B3033", "Level Head - Upgrade")
sheet.set("A3034", "305758"); sheet.set("B3034", "Elevation 1")
sheet.set("A3035", "305803"); sheet.set("B3035", "Name")
sheet.set("A3036", "305808"); sheet.set("B3036", "Na")
sheet.set("A3037", "305808"); sheet.set("B3037", "Name")
sheet.set("A3038", "185285764"); sheet.set("B3038", "Filled ")
sheet.set("A3039", "284582"); sheet.set("B3039", "EQ")
sheet.set("A3040", "284585"); sheet.set("B3040", "Arial")
sheet.set("A3041", "284590"); sheet.set("B3041", "SecretInternalLinAngArrowhead547r36186")
sheet.set("A3042", "284593"); sheet.set("B3042", "EQ")
sheet.set("A3043", "284596"); sheet.set("B3043", "Arial")
sheet.set("A3044", "284601"); sheet.set("B3044", "SecretInternalRadArrowhead5473618n4")
sheet.set("A3045", "284604"); sheet.set("B3045", "EQ")
sheet.set("A3046", "284607"); sheet.set("B3046", "Arial")
sheet.set("A3047", "284612"); sheet.set("B3047", "SecretInternalTypePreviewgArrowhead5478765182")
sheet.set("A3048", "284615"); sheet.set("B3048", "D:\\Work Area\\structural\\7.0\\rotating beam\\metric profiles\\steel\\")
sheet.set("A3049", "284678"); sheet.set("B3049", "Center (Front/Back)")
sheet.set("A3050", "284680"); sheet.set("B3050", "Center (Left/Right)")
sheet.set("A3051", "284681"); sheet.set("B3051", "ÿ ")
sheet.set("A3052", "284760"); sheet.set("B3052", "bf")
sheet.set("A3053", "284775"); sheet.set("B3053", "EQ")
sheet.set("A3054", "284818"); sheet.set("B3054", "EQ")
sheet.set("A3055", "277265"); sheet.set("B3055", "EQ")
sheet.set("A3056", "277268"); sheet.set("B3056", "Arial")
sheet.set("A3057", "277273"); sheet.set("B3057", "SecretInternalLinAngArrowhead54736k182")
sheet.set("A3058", "277276"); sheet.set("B3058", "EQ")
sheet.set("A3059", "277279"); sheet.set("B3059", "Arial")
sheet.set("A3060", "277284"); sheet.set("B3060", "SecretInternalRadArrowhead5473s6187")
sheet.set("A3061", "277287"); sheet.set("B3061", "EQ")
sheet.set("A3062", "277290"); sheet.set("B3062", "Arial")
sheet.set("A3063", "277295"); sheet.set("B3063", "SecretInternalTypePreviewgArrowhead5478765182")
sheet.set("A3064", "277298"); sheet.set("B3064", "C:\\pf_root\\9.0\\Data\\Platform\\Metric\\Library\\Annotations\\")
sheet.set("A3065", "277325"); sheet.set("B3065", "Arrowhead 1")
sheet.set("A3066", "277365"); sheet.set("B3066", "101")
sheet.set("A3067", "277434"); sheet.set("B3067", "150 m2")
sheet.set("A3068", "277444"); sheet.set("B3068", "Volume")
sheet.set("A3069", "290290"); sheet.set("B3069", "EQ")
sheet.set("A3070", "290293"); sheet.set("B3070", "Arial")
sheet.set("A3071", "290298"); sheet.set("B3071", "SecretInternalLinAngArrowhead547r36186")
sheet.set("A3072", "290301"); sheet.set("B3072", "EQ")
sheet.set("A3073", "290304"); sheet.set("B3073", "Arial")
sheet.set("A3074", "290309"); sheet.set("B3074", "SecretInternalRadArrowhead5473s6187")
sheet.set("A3075", "290312"); sheet.set("B3075", "EQ")
sheet.set("A3076", "290315"); sheet.set("B3076", "Arial")
sheet.set("A3077", "290320"); sheet.set("B3077", "SecretInternalTypePreviewgArrowhead5478765182")
sheet.set("A3078", "290323"); sheet.set("B3078", "\\\\manbsdsrv02\\docs\\bsd\\Architectural_Tutorials\\Revit_Architecture_2010_Tutorials\\Imperial Datasets\\08 - Adding Other Elements\\")
sheet.set("A3079", "290333"); sheet.set("B3079", "Ref. Level")
sheet.set("A3080", "290333"); sheet.set("B3080", "Re")
sheet.set("A3081", "290333"); sheet.set("B3081", "ÿT")
sheet.set("A3082", "290333"); sheet.set("B3082", "br")
sheet.set("A3083", "290333"); sheet.set("B3083", "Ët")
sheet.set("A3084", "290333"); sheet.set("B3084", "Ít")
sheet.set("A3085", "290630"); sheet.set("B3085", "Baluster Material")
sheet.set("A3086", "275375"); sheet.set("B3086", "EQ")
sheet.set("A3087", "275378"); sheet.set("B3087", "Arial")
sheet.set("A3088", "275383"); sheet.set("B3088", "SecretInternalLinAngArrowhead54736k182")
sheet.set("A3089", "275386"); sheet.set("B3089", "EQ")
sheet.set("A3090", "275389"); sheet.set("B3090", "Arial")
sheet.set("A3091", "275394"); sheet.set("B3091", "SecretInternalRadArrowhead5473s6187")
sheet.set("A3092", "275397"); sheet.set("B3092", "EQ")
sheet.set("A3093", "275400"); sheet.set("B3093", "Arial")
sheet.set("A3094", "275405"); sheet.set("B3094", "SecretInternalTypePreviewgArrowhead5478765182")
sheet.set("A3095", "275408"); sheet.set("B3095", "C:\\pf_root\\dev\\Data\\Platform\\Metric\\Library\\Annotations\\")
sheet.set("A3096", "275547"); sheet.set("B3096", "Boxed")
sheet.set("A3097", "275553"); sheet.set("B3097", "System Panel")
sheet.set("A3098", "275555"); sheet.set("B3098", "Wall")
sheet.set("A3099", "286948"); sheet.set("B3099", "EQ")
sheet.set("A3100", "286951"); sheet.set("B3100", "Arial")
sheet.set("A3101", "286956"); sheet.set("B3101", "SecretInternalLinAngArrowhead54736k182")
sheet.set("A3102", "286959"); sheet.set("B3102", "EQ")
sheet.set("A3103", "286962"); sheet.set("B3103", "Arial")
sheet.set("A3104", "286967"); sheet.set("B3104", "SecretInternalRadArrowhead5473s6187")
sheet.set("A3105", "286970"); sheet.set("B3105", "EQ")
sheet.set("A3106", "286973"); sheet.set("B3106", "Arial")
sheet.set("A3107", "286978"); sheet.set("B3107", "SecretInternalTypePreviewgArrowhead5478765182")
sheet.set("A3108", "286981"); sheet.set("B3108", "C:\\Documents and Settings\\All Users\\Application Data\\Autodesk\\RAC 2009\\Metric Library\\Annotations\\Civil\\")
sheet.set("A3109", "287001"); sheet.set("B3109", "Arrowhead 1")
sheet.set("A3110", "287061"); sheet.set("B3110", "90 00' 00\"")
sheet.set("A3111", "287064"); sheet.set("B3111", "Detail View 1")
sheet.set("A3112", "287122"); sheet.set("B3112", "90.00")
sheet.set("A3113", "287124"); sheet.set("B3113", "Sim")
sheet.set("A3114", "296168"); sheet.set("B3114", "EQ")
sheet.set("A3115", "296171"); sheet.set("B3115", "Arial")
sheet.set("A3116", "296176"); sheet.set("B3116", "SecretInternalLinAngArrowhead547r36186")
sheet.set("A3117", "296179"); sheet.set("B3117", "EQ")
sheet.set("A3118", "296182"); sheet.set("B3118", "Arial")
sheet.set("A3119", "296187"); sheet.set("B3119", "SecretInternalRadArrowhead5473618n4")
sheet.set("A3120", "296190"); sheet.set("B3120", "EQ")
sheet.set("A3121", "296193"); sheet.set("B3121", "Arial")
sheet.set("A3122", "296198"); sheet.set("B3122", "SecretInternalTypePreviewgArrowhead5478765182")
sheet.set("A3123", "296201"); sheet.set("B3123", "D:\\Work Area\\structural\\7.0\\rotating beam\\metric profiles\\steel\\")
sheet.set("A3124", "296264"); sheet.set("B3124", "Center (Front/Back)")
sheet.set("A3125", "296266"); sheet.set("B3125", "Center (Left/Right)")
sheet.set("A3126", "296267"); sheet.set("B3126", "ÿ ")
sheet.set("A3127", "296346"); sheet.set("B3127", "bf")
sheet.set("A3128", "296361"); sheet.set("B3128", "EQ")
sheet.set("A3129", "296404"); sheet.set("B3129", "EQ")
sheet.set("A3130", "283936"); sheet.set("B3130", "EQ")
sheet.set("A3131", "283939"); sheet.set("B3131", "Arial")
sheet.set("A3132", "283944"); sheet.set("B3132", "SecretInternalLinAngArrowhead54736k182")
sheet.set("A3133", "283947"); sheet.set("B3133", "EQ")
sheet.set("A3134", "283950"); sheet.set("B3134", "Arial")
sheet.set("A3135", "283955"); sheet.set("B3135", "SecretInternalRadArrowhead5473s6187")
sheet.set("A3136", "283958"); sheet.set("B3136", "EQ")
sheet.set("A3137", "283961"); sheet.set("B3137", "Arial")
sheet.set("A3138", "283966"); sheet.set("B3138", "SecretInternalTypePreviewgArrowhead5478765182")
sheet.set("A3139", "283969"); sheet.set("B3139", "C:\\pf_root\\dev\\Data\\Platform\\Metric\\Library\\Annotations\\")
sheet.set("A3140", "284015"); sheet.set("B3140", "Solid Black")
sheet.set("A3141", "295923"); sheet.set("B3141", "EQ")
sheet.set("A3142", "295926"); sheet.set("B3142", "Arial")
sheet.set("A3143", "295931"); sheet.set("B3143", "SecretInternalLinAngArrowhead547r36186")
sheet.set("A3144", "295934"); sheet.set("B3144", "EQ")
sheet.set("A3145", "295937"); sheet.set("B3145", "Arial")
sheet.set("A3146", "295942"); sheet.set("B3146", "SecretInternalRadArrowhead5473618n4")
sheet.set("A3147", "295945"); sheet.set("B3147", "EQ")
sheet.set("A3148", "295948"); sheet.set("B3148", "Arial")
sheet.set("A3149", "295953"); sheet.set("B3149", "SecretInternalTypePreviewgArrowhead5478765182")
sheet.set("A3150", "295956"); sheet.set("B3150", "D:\\Work Area\\structural\\7.0\\rotating beam\\metric profiles\\steel\\")
sheet.set("A3151", "296019"); sheet.set("B3151", "Center (Front/Back)")
sheet.set("A3152", "296021"); sheet.set("B3152", "Center (Left/Right)")
sheet.set("A3153", "296101"); sheet.set("B3153", "bf")
sheet.set("A3154", "296116"); sheet.set("B3154", "EQ")
sheet.set("A3155", "296150"); sheet.set("B3155", "EQ")
sheet.set("A3156", "306385"); sheet.set("B3156", "EQ")
sheet.set("A3157", "306388"); sheet.set("B3157", "Arial")
sheet.set("A3158", "306393"); sheet.set("B3158", "SecretInternalLinAngArrowhead547r36186")
sheet.set("A3159", "306396"); sheet.set("B3159", "EQ")
sheet.set("A3160", "306399"); sheet.set("B3160", "Arial")
sheet.set("A3161", "306404"); sheet.set("B3161", "SecretInternalRadArrowhead5473s6187")
sheet.set("A3162", "306407"); sheet.set("B3162", "EQ")
sheet.set("A3163", "306410"); sheet.set("B3163", "Arial")
sheet.set("A3164", "306415"); sheet.set("B3164", "SecretInternalTypePreviewgArrowhead5478765182")
sheet.set("A3165", "306418"); sheet.set("B3165", "C:\\My Documents\\2009 Revit Architecture\\Tutorials\\Rendering\\")
sheet.set("A3166", "306454"); sheet.set("B3166", "Center (Front/Back)")
sheet.set("A3167", "306456"); sheet.set("B3167", "Center (Left/Right)")
sheet.set("A3168", "306507"); sheet.set("B3168", "View 1")
sheet.set("A3169", "306517"); sheet.set("B3169", "ÿl")
sheet.set("A3170", "306529"); sheet.set("B3170", "Section Head - Min")
sheet.set("A3171", "306542"); sheet.set("B3171", "Elevation 1")
sheet.set("A3172", "306593"); sheet.set("B3172", "r4")
sheet.set("A3173", "306598"); sheet.set("B3173", "Section Head - Min")
sheet.set("A3174", "306600"); sheet.set("B3174", "Section Head - Min")
sheet.set("A3175", "306622"); sheet.set("B3175", "Level Head - Upgrade")
sheet.set("A3176", "306635"); sheet.set("B3176", "Elevation 1")
sheet.set("A3177", "306680"); sheet.set("B3177", "Name")
sheet.set("A3178", "306705"); sheet.set("B3178", "Filled Elevation Target Ä")
sheet.set("A3179", "306711"); sheet.set("B3179", "1/4\"")
sheet.set("A3180", "306719"); sheet.set("B3180", "Section Tail - Upgrade")
sheet.set("A3181", "306746"); sheet.set("B3181", "3/16\" 1/2\"")
sheet.set("A3182", "306748"); sheet.set("B3182", "3/32\" 3/8\"")
sheet.set("A3183", "306876"); sheet.set("B3183", "RPC Shruba")
sheet.set("A3184", "306900"); sheet.set("B3184", "ÿJ")
sheet.set("A3185", "306902"); sheet.set("B3185", "ÿJ")
sheet.set("A3186", "306904"); sheet.set("B3186", "ÿJ")
sheet.set("A3187", "306906"); sheet.set("B3187", "ÿJ")
sheet.set("A3188", "306908"); sheet.set("B3188", "ÿJ")
sheet.set("A3189", "306910"); sheet.set("B3189", "ÿJ")
sheet.set("A3190", "306912"); sheet.set("B3190", "ÿJ")
sheet.set("A3191", "306914"); sheet.set("B3191", "ÿJ")
sheet.set("A3192", "306916"); sheet.set("B3192", "ÿJ")
sheet.set("A3193", "306918"); sheet.set("B3193", "ÿJ")
sheet.set("A3194", "306920"); sheet.set("B3194", "ÿJ")
sheet.set("A3195", "306922"); sheet.set("B3195", "ÿJ")
sheet.set("A3196", "306924"); sheet.set("B3196", "ÿJ")
sheet.set("A3197", "306926"); sheet.set("B3197", "ÿJ")
sheet.set("A3198", "306928"); sheet.set("B3198", "ÿJ")
sheet.set("A3199", "306930"); sheet.set("B3199", "ÿJ")
sheet.set("A3200", "306932"); sheet.set("B3200", "ÿJ")
sheet.set("A3201", "306934"); sheet.set("B3201", "ÿJ")
sheet.set("A3202", "306936"); sheet.set("B3202", "ÿJ")
sheet.set("A3203", "306938"); sheet.set("B3203", "ÿJ")
sheet.set("A3204", "306940"); sheet.set("B3204", "ÿJ")
sheet.set("A3205", "306942"); sheet.set("B3205", "ÿJ")
sheet.set("A3206", "306944"); sheet.set("B3206", "ÿJ")
sheet.set("A3207", "306946"); sheet.set("B3207", "ÿJ")
sheet.set("A3208", "306948"); sheet.set("B3208", "ÿJ")
sheet.set("A3209", "306950"); sheet.set("B3209", "ÿJ")
sheet.set("A3210", "306952"); sheet.set("B3210", "ÿJ")
sheet.set("A3211", "306954"); sheet.set("B3211", "ÿJ")
sheet.set("A3212", "306956"); sheet.set("B3212", "ÿJ")
sheet.set("A3213", "306958"); sheet.set("B3213", "ÿJ")
sheet.set("A3214", "306960"); sheet.set("B3214", "ÿJ")
sheet.set("A3215", "306962"); sheet.set("B3215", "ÿJ")
sheet.set("A3216", "306960"); sheet.set("B3216", "ÿJ")
sheet.set("A3217", "306962"); sheet.set("B3217", "ÿJ")
sheet.set("A3218", "306962"); sheet.set("B3218", "@&")
sheet.set("A3219", "24"); sheet.set("B3219", "ed")
sheet.set("A3220", "65561"); sheet.set("B3220", "ed")
sheet.set("A3221", "65568"); sheet.set("B3221", "Ò{")
sheet.set("A3222", "65569"); sheet.set("B3222", "om")
sheet.set("A3223", "65570"); sheet.set("B3223", "@{")
sheet.set("A3224", "65571"); sheet.set("B3224", "@{")
sheet.set("A3225", "65572"); sheet.set("B3225", "@{")
sheet.set("A3226", "65573"); sheet.set("B3226", "@{")
sheet.set("A3227", "65574"); sheet.set("B3227", "@{")
sheet.set("A3228", "65575"); sheet.set("B3228", "@{")
sheet.set("A3229", "65576"); sheet.set("B3229", "@{")
sheet.set("A3230", "65577"); sheet.set("B3230", "@{")
sheet.set("A3231", "65578"); sheet.set("B3231", "@{")
sheet.set("A3232", "65579"); sheet.set("B3232", "@{")
sheet.set("A3233", "304350"); sheet.set("B3233", "EQ")
sheet.set("A3234", "304353"); sheet.set("B3234", "Arial")
sheet.set("A3235", "304358"); sheet.set("B3235", "SecretInternalLinAngArrowhead547r36186")
sheet.set("A3236", "304361"); sheet.set("B3236", "EQ")
sheet.set("A3237", "304364"); sheet.set("B3237", "Arial")
sheet.set("A3238", "304369"); sheet.set("B3238", "SecretInternalRadArrowhead5473s6187")
sheet.set("A3239", "304372"); sheet.set("B3239", "EQ")
sheet.set("A3240", "304375"); sheet.set("B3240", "Arial")
sheet.set("A3241", "304380"); sheet.set("B3241", "SecretInternalTypePreviewgArrowhead5478765182")
sheet.set("A3242", "304383"); sheet.set("B3242", "C:\\Documents and Settings\\All Users\\Application Data\\Autodesk\\RAC 2009\\Imperial Library\\")
sheet.set("A3243", "304420"); sheet.set("B3243", "Center F/B")
sheet.set("A3244", "304422"); sheet.set("B3244", "Center L/R")
sheet.set("A3245", "304490"); sheet.set("B3245", "Section Head - Min")
sheet.set("A3246", "304503"); sheet.set("B3246", "Elevation 1")
sheet.set("A3247", "304559"); sheet.set("B3247", "Section Head - Min")
sheet.set("A3248", "304561"); sheet.set("B3248", "Section Head - Min")
sheet.set("A3249", "304587"); sheet.set("B3249", "Profile plane")
sheet.set("A3250", "304591"); sheet.set("B3250", "ÿ'")
sheet.set("A3251", "304633"); sheet.set("B3251", "ÿ|")
sheet.set("A3252", "304635"); sheet.set("B3252", "ÿx")
sheet.set("A3253", "304637"); sheet.set("B3253", "ÿ{")
sheet.set("A3254", "304642"); sheet.set("B3254", "View 1")
sheet.set("A3255", "304661"); sheet.set("B3255", "ÿK")
sheet.set("A3256", "304697"); sheet.set("B3256", "ÿ(")
sheet.set("A3257", "304703"); sheet.set("B3257", "ÿ+")
sheet.set("A3258", "304710"); sheet.set("B3258", "ÿ?")
sheet.set("A3259", "304711"); sheet.set("B3259", "ÿE")
sheet.set("A3260", "304712"); sheet.set("B3260", "ÿ?")
sheet.set("A3261", "304713"); sheet.set("B3261", "ÿ?")
sheet.set("A3262", "304714"); sheet.set("B3262", "ÿW")
sheet.set("A3263", "304717"); sheet.set("B3263", "Profile plane")
sheet.set("A3264", "304750"); sheet.set("B3264", "Filled Elevation Target Ä")
sheet.set("A3265", "304763"); sheet.set("B3265", "Level Head - Upgrade")
sheet.set("A3266", "304776"); sheet.set("B3266", "Elevation 1")
sheet.set("A3267", "304821"); sheet.set("B3267", "Name")
sheet.set("A3268", "304846"); sheet.set("B3268", "Filled Elevation Target Ä")
sheet.set("A3269", "304852"); sheet.set("B3269", "1/4\"")
doc.recompute()
print("revit-free: documento criado —", len(doc.Objects), "objetos")
